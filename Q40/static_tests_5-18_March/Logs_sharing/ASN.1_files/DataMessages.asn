DataMessages DEFINITIONS
AUTOMATIC TAGS ::=

BEGIN

EXPORTS ALL ;

IMPORTS
    Pad1bits, Pad2bits, Pad3bits, Pad4bits, Pad5bits, Pad6bits, Pad7bits, Pad8bits,
    Pad9bits, Pad10bits, Pad11bits, Pad12bits, Pad13bits, Pad14bits, Pad15bits,
    Unsigned1, Unsigned2, Unsigned3, Unsigned4, Unsigned5, Unsigned6, Unsigned7,
    Unsigned8, Unsigned9, Unsigned10, Unsigned11, Unsigned12, Unsigned13, Unsigned14,
    Unsigned15, Unsigned16, Unsigned17, Unsigned20, Unsigned21, Unsigned24,
    Unsigned32, Unsigned33,
    Signed3, Signed4, Signed5, Signed6, Signed7, Signed8, Signed9, Signed10, Signed11,
    Signed12, Signed13, Signed14, Signed15, Signed16, Signed17, Signed18, Signed19,
    Signed20, Signed21, Signed22, Signed23, Signed24, Signed25, Signed26, Signed27,
    Signed28, Signed30, Signed31, Signed32, Signed33, Signed35, Signed40,
    IEEE754Sp, IEEE754Dp
    FROM FundamentalDataTypes

    TimeReference, DatumID, SatID, ConstellationID, MessageOctet, SignalID,
    GPSSignalID, GPSMultiSignalID, GalSignalID, GalMultiSignalID,
    BDSSignalID, BDSMultiSignalID, GLOSignalID, GLOMultiSignalID,
    SBASSignalID, SBASMultiSignalID,
    SatTrackingState, InterferenceAndJammingStatus, InterferenceAndJammingTypes,
    SpoofingAndMeaconingTypes, CyberAttackTypes, SpoofingMeaconingStatus,
    CyberAttackStatus, PositionFigureOfMerit, VelocityFigureOfMerit, QFlag,
    MultiSignalID, SatSignalHealth, GalSignalHealthIndicator, DataSource,
    TimeFigureOfMerit, PositionLLA, PositionXYZ, VelocityXYZ, VelocityENU,
    LeverArmXYZ, NavSolutionMode, RAIMMode, RAIMType, DilutionOfPrecision,
    SensorsInUse, CorrectionService, TimeStamp, DateTime, FixStatus, AngularDir,
    IonoCorrection, TropoCorrection, SatClockCorrection, MagneticVariationSource,
    NorthRef, Position, RouteID, WaypointID, WaypointIndex, LogicalTrackerID
    FROM CommonFieldDefinitions
;

-- ****************************************************************************
-- * Initialisation Input Data                                                *
-- *                                                                          *
-- * Message name:    DataInitialisationInputData                             *
-- * Message ID:      6427                                                    *
-- * Message status:  Core                                                    *
-- * Frequency:       As required                                             *
-- * Input/Output:    Input                                                   *
-- *~~~~~~~~~~~~~~~~~~~~~~~~~~~~~~~~~~~~~~~~~~~~~~~~~~~~~~~~~~~~~~~~~~~~~~~~~~*
-- * Short Description:                                                       *
-- *                                                                          *
-- * This message allows the user to provide the receiver with initial        *
-- * position, velocity and time to improve Time To First Fix (TTFF).         *
-- *                                                                          *
-- * Notes:                                                                   *
-- *                                                                          *
-- ****************************************************************************
--
DataInitialisationInputData ::= SEQUENCE {
    validityTime                    TimeStamp,
    initialisationValidity          InitialisationValidity,
    dateTime                        DateTime,
    position                        Position,
    groundSpeed                     IEEE754Sp,              -- metres/second
    track                           AngularDir              -- track bearing and reference
}

-- The receiver sets the corresponding validity field (TRUE = Valid) in message
-- TBD to indicate receipt of valid initialisation data. The receiver only uses
-- complete sets of the Time, position, velocity or lever arms components.
-- Padded to use 16 bits.
InitialisationValidity ::= SEQUENCE {
    dateTimeValid                   BOOLEAN,
    latitudeValid                   BOOLEAN,
    longitudeValid                  BOOLEAN,
    altitudeValid                   BOOLEAN,
    groundTrackValid                BOOLEAN,
    groundSpeedValid                BOOLEAN,
    reservedBits                    Pad10bits
}


-- ****************************************************************************
-- * Date Time                                                                *
-- *                                                                          *
-- * Message name:    DataDateTime                                            *
-- * Message ID:      6444                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message provides accurate time/date. This message qualifies the     *
-- * time of the preceding nPPS pulse. It can be both an output from the      *
-- * receiver or be used to provide time aiding to the receiver in            *
-- * association with a nPPS input.                                           *
-- *                                                                          *
-- * Notes:                                                                   *
-- *                                                                          *
-- * For rates up to 10PPS the absolute time of the selected nPPS pulse can   *
-- * be determined from the DataDateTime message which shall be output after  *
-- * its associated nPPS pulse and before the next nPPS pulse is output.  At  *
-- * rates above 10PPS the behaviour and timing is not standardised and shall *
-- * be as defined by the receiver supplier.  At rates up to 10PPS the host   *
-- * shall be responsible for ensuring that the total number of connected     *
-- * messages and baud rate/parity selection do not prevent the receiver from *
-- * providing DataDateTime for each nPPS pulse.                              *
-- *                                                                          *
-- * When it is to be used in coordination with the nPPS time marker output   *
-- * the DataDateTime message should be initiated by configuring the nPPS     *
-- * using CmndEnablePPSOutput, rather than by connecting to this message     *
-- * directly.                                                                *
-- *                                                                          *
-- ****************************************************************************
--
DataDateTime ::= SEQUENCE {
    validityTime                    TimeStamp,
    dateTime                        DateTime,
    estimatedTimeOffsetAccuracy     IEEE754Sp,              -- seconds (1 sigma accuracy)
    wordPadding                     Pad8bits,
    port                            INTEGER (0..255)        -- Port Number of the PPS output
}


-- ****************************************************************************
-- * Event Date Time                                                          *
-- *                                                                          *
-- * Message name:    DataEventDateTime                                       *
-- * Message ID:      6252                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message reports the time associated with an input pulse on one of   *
-- * the receiver's event marker inputs.                                      *
-- *                                                                          *
-- * Notes:                                                                   *
-- *                                                                          *
-- ****************************************************************************
--
DataEventDateTime ::= SEQUENCE {
    validityTime                    TimeStamp,
    dateTime                        DateTime,
    estimatedTimeOffsetAccuracy     IEEE754Sp,              -- seconds (1 sigma accuracy)
    wordPadding                     Pad8bits,
    port                            INTEGER (0..255)        -- Port Number of the event marker input
}


-- ****************************************************************************
-- * Semi Precise Date Time Transfer/Aiding                                   *
-- *                                                                          *
-- * Message name:    DataSemiPreciseDateTime                                 *
-- * Message ID:      6299                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message allows semi precise time transfer without the need to       *
-- * utilise a discrete timing marker. The achieved time accuracy depends on  *
-- * the accuracy with which the message is transmitted. The total estimated  *
-- * time uncertainty includes both the uncertainty with which the source     *
-- * knows time and the uncertainty in propagation time.                      *
-- *                                                                          *
-- * Notes:                                                                   *
-- *                                                                          *
-- * This message allows semi precise time transfer in either direction. The  *
-- * fully qualified semi-precise time can be determined from the dateTime    *
-- * field and the sub-second component of TOW in validityTime. The timing    *
-- * reference for the message is the start time of the message               *
-- * synchronisation word (SOH/DEL).                                          *
-- *                                                                          *
-- * The field 'timeUncertainty' indicates to the receiving end of the        *
-- * transfer how accurately the time transfer is expected to be but it is    *
-- * additionally subject to the accuracy with which the receiving end is     *
-- * able to recover and process the message and delays in the transmission   *
-- * path.                                                                    *
-- *                                                                          *
-- * To achieve time transfer from the receiver to host, the host will        *
-- * connect to this message as normal for the required duration. To provide  *
-- * semi-precise time aiding to a receiver, the host sends this message to   *
-- * the receiver.                                                            *
-- *                                                                          *
-- * It is the responsibility of the host to manage the number of connected   *
-- * messages in order to maximise the achievable accuracy. Accuracy is       *
-- * likely to be improved by making use of multiple message transmissions.   *
-- *                                                                          *
-- * This message is only intended to support semi-precise time between the   *
-- * receiver and a locally connected host. Where time transfer is required   *
-- * to a remote host other standard transfer protocols should be utilised    *
-- * between the local and remote host.                                       *
-- *                                                                          *
-- ****************************************************************************
--
DataSemiPreciseDateTime ::= SEQUENCE {
    validityTime                    TimeStamp,
    dateTime                        DateTime,
    timeUncertainty                 IEEE754Sp               -- seconds (estimated accuracy of time transferred)
}


-- ****************************************************************************
-- * PVT Message                                                              *
-- *                                                                          *
-- * Message name:    DataPVT                                                 *
-- * Message ID:      6349                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message provides a short PVT message and can be used as an          *
-- * alternative to the Core Navigation Dataset Message.                      *
-- *                                                                          *
-- * Notes:                                                                   *
-- *                                                                          *
-- * Refer to National Geospatial-Intelligence Agency Standardization         *
-- * Document, Universal Grids and Grid Reference Systems.                    *
-- *                                                                          *
-- * Position measurements use Latitude, Longitude, Altitude (degrees,        *
-- * degrees, metres) or a selected Grid Eastings, Northings, Altitude        *
-- * (metres, metres, metres) using the selected datum coordinate system and  *
-- * altitude reference.                                                      *
-- *                                                                          *
-- * FixStatus = none (0), indicates that no PVT is available.                *
-- * In such a scenario it is recommended that the following values are used: *
-- * - position = [0,0,0] (DatumID, AltitudeRef, PositionFormatID)            *
-- * -            [0,0,-6378137] (latitude, longitude, altitude)              *
-- * - groundSpeed = [0]                                                      *
-- * - track = [0,0] (bearing, NorthRef)                                      *
-- * - estimated Errors = maximum value of variable type                      *
-- *                                                                          *
-- ****************************************************************************
--
DataPVT ::= SEQUENCE {
    validityTime                    TimeStamp,
    dateTime                        DateTime,
    position                        Position,               -- see Notes
    groundSpeed                     IEEE754Sp,              -- metres/second
    track                           AngularDir,             -- track bearing and reference
    geoidEllipsoidSeparation        IEEE754Sp,              -- metres (gives the geoid minus ellipsoid value)
    magneticVariation               IEEE754Sp,              -- degrees (-180.0 <= value < +180.0) positive when magnetic North is East of true North
    wordPadding                     Pad4bits,
    magneticVariationSource         MagneticVariationSource,
    qFlag                           QFlag,
    encryptedServiceUsed            BOOLEAN,                -- True if at least one encrypted service has been utilised
    authenticatedServiceUsed        BOOLEAN,                -- True if at least one authenticated service has been utilised
    fixAided                        BOOLEAN,
    wordPadding1                    Pad4bits,
    fixStatus                       FixStatus,
    positionFigureOfMerit           PositionFigureOfMerit,  -- 3-D position FOM
    velocityFigureOfMerit           VelocityFigureOfMerit,
    timeFigureOfMerit               TimeFigureOfMerit
}


-- ****************************************************************************
-- * Core Navigation Solution                                                 *
-- *                                                                          *
-- * Message name:    DataCoreNavSolution                                     *
-- * Message ID:      6402                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * The core navigation solution dataset returns a navigation solution       *
-- * together with estimated errors and information on the quality of the     *
-- * integrated navigation solution which has been calculated using one or    *
-- * more navigation sensors (e.g. GNSS and INS).                             *
-- *                                                                          *
-- * Notes:                                                                   *
-- *                                                                          *
-- * Position measurements use Latitude, Longitude, Altitude (degrees,        *
-- * degrees, metres above ellipsoid) using the selected datum coordinate     *
-- * system. Velocity measurements use East, North, Up (metres, metres,       *
-- * metres) using the selected datum coordinate system.                      *
-- *                                                                          *
-- * FixStatus = none (0), indicates that no PVT is available.                *
-- * In such a scenario it is recommended that the following values are used: *
-- * - position = [0,0,-6378137]                                              *
-- * - heightAboveGeoid = [0]                                                 *
-- * - velocity = [0,0,0]                                                     *
-- * - estimated Errors = maximum value of variable type                      *
-- *                                                                          *
-- * When this message is transmitted by a GNSS sensor the errors defined     *
-- * within are calculated by the GNSS sensor itself. When it is              *
-- * transmitted by a combined GNSS sensor and an inertial sensor the         *
-- * errors defined within are calculated by the combined navigation system.  *
-- *                                                                          *
-- * The reported errors do not include datum transformation errors and       *
-- * users should seek clarification from vendors about their specific        *
-- * implementations.                                                         *
-- *                                                                          *
-- ****************************************************************************
--
DataCoreNavSolution ::= SEQUENCE {
    validityTime                    TimeStamp,
    dateTime                        DateTime,
    position                        PositionLLA,            -- Lat, Lon and Altitude (height above ellipsoid) - see Notes
    heightAboveGeoid                IEEE754Dp,              -- metres (height above the WGS-84 geoid )
    velocity                        VelocityENU,            -- see Notes
    magneticVariation               IEEE754Sp,
    wordPadding                     Pad4bits,
    magneticVariationSource         MagneticVariationSource,
    qFlag                           QFlag,
    encryptedServiceUsed            BOOLEAN,                -- True if at least one encrypted service has been utilised
    authenticatedServiceUsed        BOOLEAN,                -- True if at least one authenticated service has been utilised
    fixAided                        BOOLEAN,
    wordPadding1                    Pad4bits,
    datumID                         DatumID,
    estimatedHorizPosErr            IEEE754Sp,              -- metres (1 sigma accuracy)
    estimatedVertPosErr             IEEE754Sp,              -- metres (1 sigma accuracy)
    estimatedTimeError              IEEE754Sp,              -- seconds (1 sigma accuracy)
    estimatedHorizVelErr            IEEE754Sp,              -- metres/second (1 sigma accuracy)
    estimatedVertVelErr             IEEE754Sp,              -- metres/second (1 sigma accuracy)
    estimatedTimeRateErr            IEEE754Sp,              -- seconds/second (1 sigma accuracy)
    wordPadding2                    Pad4bits,
    fixStatus                       FixStatus,
    altitudeHeld                    BOOLEAN,                -- True if altitude is not calculated in the navigation solution but is set to a fixed/known value
    clockHeld                       BOOLEAN,                -- True if clock bias is not calculated in the navigation solution but is set to a fixed/known value
    leverArmInUse                   BOOLEAN,
    wordPadding3                    Pad5bits,
    timeSinceLastGoodFix            INTEGER (0..255),       -- seconds (0 indicates < 1 seconds, 255 indicates > 254 seconds)
    timeSinceLastNavSolModeChange   INTEGER (0..255),       -- seconds (0 indicates < 1 seconds, 255 indicates > 254 seconds)
    satsInSolution                  Unsigned8,              -- total number of satellites used in the solution
    satsInSolutionWithThreshCN0     Unsigned8,              -- Refers to the number of satellites in solution with a C/N0 > 30 dB/Hz for at least one signal
    satsInSolutionTrackedInState5   Unsigned8,              -- Refers to the number of satellites in solution tracked in State 5 (carrier phase tracking and demodulating data)
    navSolutionMode                 NavSolutionMode,
    raimMode                        RAIMMode,
    dilutionOfPrecision             DilutionOfPrecision,    -- DOP is determined from the satellites in use only.  A DOP over 6 indicates an unstable navigation solution.
    sensorsInUse                    SensorsInUse,
    ionoCorrectionInUse             IonoCorrection,
    tropoCorrectionInUse            TropoCorrection,
    correctionsInUse                CorrectionService,
    wordPadding4                    Pad4bits,
    leverArmValue                   LeverArmXYZ,
    servicesInUse                   MultiSignalID
}


-- ****************************************************************************
-- * Core ECEF Navigation solution                                            *
-- *                                                                          *
-- * Message name:    DataCoreECEFNavSolution                                 *
-- * Message ID:      6269                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * The core ECEF navigation solution dataset returns an ECEF navigation     *
-- * solution together with error estimates and information on the quality    *
-- * of the integrated navigation solution which has been calculated using    *
-- * one or more navigation sensors (e.g. GNSS and INS).                      *
-- *                                                                          *
-- * Notes:                                                                   *
-- *                                                                          *
-- * Position and Velocity measurements use an ECEF coordinate system with    *
-- * the WGS-84 datum origin.                                                 *
-- *                                                                          *
-- * FixStatus = none (0), indicates that no PVT is available.                *
-- * In such a scenario it is recommended that the following values are used: *
-- * - position = [0,0,0]                                                     *
-- * - velocity = [0,0,0]                                                     *
-- * - estimated Errors = maximum value of variable type                      *
-- *                                                                          *
-- * When this message is transmitted by a GNSS sensor the errors defined     *
-- * within are calculated by the GNSS sensor itself. When it is              *
-- * transmitted by a combined GNSS sensor and an inertial sensor the         *
-- * errors defined within are calculated by the combined navigation system.  *
-- *                                                                          *
-- ****************************************************************************
--
DataCoreECEFNavSolution ::= SEQUENCE {
    validityTime                    TimeStamp,
    dateTime                        DateTime,
    position                        PositionXYZ,
    velocity                        VelocityXYZ,
    qFlag                           QFlag,
    encryptedServiceUsed            BOOLEAN,                -- True if at least one encrypted service has been utilised
    authenticatedServiceUsed        BOOLEAN,                -- True if at least one authenticated service has been utilised
    fixAided                        BOOLEAN,
    wordPadding                     Pad12bits,
    estimatedXPosErr                IEEE754Sp,              -- metres (1 sigma accuracy)
    estimatedYPosErr                IEEE754Sp,              -- metres (1 sigma accuracy)
    estimatedZPosErr                IEEE754Sp,              -- metres (1 sigma accuracy)
    estimatedTimeError              IEEE754Sp,              -- seconds (1 sigma accuracy)
    estimatedXVelErr                IEEE754Sp,              -- metres/second (1 sigma accuracy)
    estimatedYVelErr                IEEE754Sp,              -- metres/second (1 sigma accuracy)
    estimatedZVelErr                IEEE754Sp,              -- metres/second (1 sigma accuracy)
    estimatedTimeRateErr            IEEE754Sp,              -- seconds/second (1 sigma accuracy)
    wordPadding1                    Pad4bits,
    fixStatus                       FixStatus,
    altitudeHeld                    BOOLEAN,                -- True if altitude is not calculated in the navigation solution but is set to a fixed/known value
    clockHeld                       BOOLEAN,                -- True if clock bias is not calculated in the navigation solution but is set to a fixed/known value
    leverArmInUse                   BOOLEAN,
    wordPadding2                    Pad5bits,
    timeSinceLastGoodFix            INTEGER (0..255),       -- seconds (0 indicates < 1 seconds, 255 indicates > 254 seconds)
    timeSinceLastNavSolModeChange   INTEGER (0..255),       -- seconds (0 indicates < 1 seconds, 255 indicates > 254 seconds)
    satsInSolution                  Unsigned8,              -- total number of satellites used in the solution
    satsInSolutionWithThreshCN0     Unsigned8,              -- Refers to the number of satellites in solution with a C/N0 > 30 dB/Hz for at least one signal
    satsInSolutionTrackedInState5   Unsigned8,              -- Refers to the number of satellites in solution tracked in State 5 (carrier phase tracking and demodulating data)
    navSolutionMode                 NavSolutionMode,
    raimMode                        RAIMMode,
    dilutionOfPrecision             DilutionOfPrecision,    -- DOP is determined from the satellites in use only. A DOP over 6 indicates an unstable navigation solution.
    sensorsInUse                    SensorsInUse,
    ionoCorrectionInUse             IonoCorrection,
    tropoCorrectionInUse            TropoCorrection,
    correctionsInUse                CorrectionService,
    wordPadding3                    Pad4bits,
    leverArmValue                   LeverArmXYZ,
    servicesInUse                   MultiSignalID
}


-- ****************************************************************************
-- * Core ECEF Nav Covariance matrix                                          *
-- *                                                                          *
-- * Message name:    DataCoreECEFNavCovariance                               *
-- * Message ID:      6420                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * Returns the diagonal and off-diagonal (single sided) elements of the     *
-- * symmetric covariance matrix of the position and velocity components (in  *
-- * ECEF) of the navigation solution state vector.                           *
-- *                                                                          *
-- * Notes:                                                                   *
-- *                                                                          *
-- * The diagram below shows the order of transmission of the covariance      *
-- * matrix with the position variance (X,Y,Z) and velocity variance          *
-- * (X',Y',Z') information on the diagonal axis. Only the upper right of     *
-- * the matrix is sent (elements marked '.' are not sent). This is because   *
-- * the covariance matrix is symmetrical around the diagonal. The off        *
-- * diagonal elements, the covariances, describe the correlations between    *
-- * the errors in the different state vector estimates.                      *
-- *                                                                          *
-- * The units of the measurements that the covariance is derived for are     *
-- * metres for position and metres/s for velocity.                           *
-- *                                                                          *
-- * |           1(X)     2        3        4        5        6               *
-- * |           .        7(Y)     8        9       10       11               *
-- * |           .        .       12(Z)    13       14       15               *
-- * |           .        .        .       16(X')   17       18               *
-- * |           .        .        .        .       19(Y')   20               *
-- * |           .        .        .        .        .       21(Z')           *
-- *                                                                          *
-- * The validity time may be used to associate the covariance matrix with    *
-- * core nav data measurements in the same measurement epoch.                *
-- *                                                                          *
-- ****************************************************************************
--
DataCoreECEFNavCovariance ::= SEQUENCE {
    validityTime                                TimeStamp,
    covMatrix                                   SEQUENCE (SIZE(21)) OF IEEE754Sp
}


-- ****************************************************************************
-- * RAIM Statistics and Integrity                                            *
-- *                                                                          *
-- * Message name:    DataRAIMStats                                           *
-- * Message ID:      6265                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message contains the Receiver Autonomous Integrity Monitor (RAIM)   *
-- * output alerts, statistics and integrity data.                            *
-- *                                                                          *
-- * Notes:                                                                   *
-- *                                                                          *
-- ****************************************************************************
--
DataRAIMStats ::= SEQUENCE {
    validityTime                    TimeStamp,
    raimType                        RAIMType,
    raimMode                        RAIMMode,
    raimIntegrity                   RAIMIntegrity,
    hERLPosition                    IEEE754Sp,              -- metres
    vERLPosition                    IEEE754Sp,              -- metres
    hERLVelocity                    IEEE754Sp,              -- metres/second
    vERLVelocity                    IEEE754Sp,              -- metres/second
    testStatistic                   IEEE754Sp               -- Overall model test statistic for the PVT, divided by the test threshold
}

RAIMIntegrity ::= SEQUENCE {
-- Padded to use 4 bits.
    integrityStatus                 ENUMERATED {
        raimIntStatusSuccessful,        -- RAIM successful
        raimIntStatusFailed,            -- RAIM failed
        raimIntStatusUnavailable,       -- RAIM unavailable
        reserved3,
        reserved4,
        reserved5,
        reserved6,
        reserved7,
        reserved8,
        reserved9,
        reserved10,
        reserved11,
        reserved12,
        reserved13,
        reserved14,
        reserved15
    },
    verticalAlarmTriggered          BOOLEAN,
    horizontalAlarmTriggered        BOOLEAN,
    navSolutionTimeAlarmTriggered   BOOLEAN,
    fSEAlarmTriggered               BOOLEAN
}


-- ****************************************************************************
-- * Threat Summary Report                                                    *
-- *                                                                          *
-- * Message name:    DataThreatSummary                                       *
-- * Message ID:      6315                                                    *
-- * Message status:  Core                                                    *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message provides a summary of any interference/jamming,             *
-- * spoofing/meaconing and RF cyber threats that have been detected and how  *
-- * the receiver is responding to these threats. It does not provide detail  *
-- * of the threats on a signal by signal basis (see                          *
-- * DataThreatDetailedReport).                                               *
-- *                                                                          *
-- * Notes:                                                                   *
-- *                                                                          *
-- ****************************************************************************
--
DataThreatSummary ::= SEQUENCE {
    validityTime                    TimeStamp,
    wordPadding                     Pad4bits,
    jammingStatus                   InterferenceAndJammingStatus,
    wordPadding1                    Pad6bits,
    spoofingStatus                  SpoofingMeaconingStatus,
    wordPadding2                    Pad6bits,
    cyberAttackStatus               CyberAttackStatus,
    wordPadding3                    Pad8bits
}


-- ****************************************************************************
-- * Threat Detailed Report                                                   *
-- *                                                                          *
-- * Message name:    DataThreatDetailedReport                                *
-- * Message ID:      6438                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message reports the Jamming/Spoofing/CyberAttack receiver status    *
-- * on a signal by signal basis (for signals that are selected for use).     *
-- *                                                                          *
-- * Notes:                                                                   *
-- *                                                                          *
-- ****************************************************************************
--
DataThreatDetailedReport ::= SEQUENCE {
    validityTime                    TimeStamp,
    numberOfMessages                Unsigned8,              -- Number of messages in this report
    messageNumber                   Unsigned8,              -- Number of message being reported (0 to N-1)
    reports                         ThreatReports
}

-- The receiver may output multiple reports, limited by the maximum message
-- length. The receiver may also choose to output this message multiple times
-- to report on different subsets of signals. The receiver will only report for
-- signals that are selected for use.
ThreatReports ::= SEQUENCE {
    wordPadding                     Pad12bits,
    threatReports                   SEQUENCE (SIZE(0..15)) OF SEQUENCE {
        gnssSignal                      SignalID,
        signalPowerMeasurementValid     BOOLEAN,
        signalPower                     Unsigned7,              -- dB-Hz: Mean received in-band signal power density (dB-Hz).  Reported as dB above -204 dBW
        wordPadding                     Pad4bits,
        interferenceJammingStatus       InterferenceAndJammingStatus,
        detectedJammingTypes            InterferenceAndJammingTypes,
        perSatInfo                      SatThreatReports
    }
}

SatThreatReports ::= SEQUENCE {
    wordPadding                     Pad10bits,
    satThreatReports                SEQUENCE (SIZE(0..63)) OF SEQUENCE {
        satID                           SatID,
        signalMeasuredJS                Unsigned8,
        wordPadding                     Pad2bits,
        jammingToSignalRatioType        ENUMERATED {
            jtsrtNotAvailable,              -- No J/S measurements available
            jtsrtRxOnly,                    -- J/S measurements assessed ref receiver input
            jtsrtAntenna                    -- J/S assessed ref antenna received signal
        },
        spoofingMeaconingStatus         SpoofingMeaconingStatus,    -- Signal Measured Jammer to Signal ratio.  Reported J/S in dB
        cyberAttackStatus               CyberAttackStatus,
        spoofingAndMeaconingTypes       SpoofingAndMeaconingTypes,
        cyberAttackTypes                CyberAttackTypes
    }
}


-- ****************************************************************************
-- * Satellite Range Information (Corrected)                                  *
-- *                                                                          *
-- * Message name:    DataCorrectedSatRangeInfo                               *
-- * Message ID:      6270                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message type is used to provide corrected GNSS satellite range      *
-- * information for all satellites being tracked by the receiver.            *
-- *                                                                          *
-- * Notes:                                                                   *
-- *                                                                          *
-- * This message can also be used to pass corrected ranging information to   *
-- * the receiver from another GNSS sensor.                                   *
-- *                                                                          *
-- ****************************************************************************
--
DataCorrectedSatRangeInfo ::= SEQUENCE {
    validityTime                    TimeStamp,
    numberOfMessages                Unsigned8,              -- Number of corrected range messages to be reported this epoch (N)
    messageNumber                   Unsigned8,              -- Number of corrected range message being reported (0 to N-1)
    wordPadding                     Pad12bits,
    navSolutionMode                 NavSolutionMode,
    signalRangeInfos                CorrectedSignalRangeInfos
}

-- Shall include multiple SignalRangeInfo objects, one per signal per satellite in the message
CorrectedSignalRangeInfos ::= SEQUENCE {
    correctedSignalRangeInfo        SEQUENCE (SIZE(0..65535)) OF SEQUENCE {
        signalRangeInfo                 SignalRangeInfo,
        satClockCorrectionInUse         SatClockCorrection,
        ionoCorrectionInUse             IonoCorrection,
        tropoCorrectionInUse            TropoCorrection,
        rxClockCorrectionInUse          BOOLEAN,
        wordPadding                     Pad3bits
    }
}

SignalRangeInfo ::= SEQUENCE {
    signalID                        SignalID,
    satID                           SatID,
    wordPadding                     Pad12bits,
    trackingState                   SatTrackingState,
    pseudoRange                     IEEE754Dp,              -- metres
    pseudoRangeRate                 IEEE754Dp,              -- metres/second
    accumulatedDeltaRange           IEEE754Dp,              -- cycles
    pseudoRangeStdDeviation         IEEE754Sp,              -- metres
    pseudoRangeRateStdDeviation     IEEE754Sp,              -- metres/second
    accumDeltaRangeStdDeviation     IEEE754Sp,              -- cycles
    cN0                             IEEE754Sp,              -- dB-Hz
    continuousTrackingTime          IEEE754Sp               -- seconds: Number of seconds of continuous tracking (no cycle slipping)
}


-- ****************************************************************************
-- * Satellite Range Information (Raw)                                        *
-- *                                                                          *
-- * Message name:    DataRawSatRangeInfo                                     *
-- * Message ID:      6359                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message type is used to provide raw (uncorrected) GNSS satellite    *
-- * range information for all satellites being tracked by the receiver.      *
-- *                                                                          *
-- * Notes:                                                                   *
-- *                                                                          *
-- * Raw measurements are not corrected for atmospheric, satellite clock or   *
-- * deliberately introduced range errors. This message can also be used to   *
-- * pass ranging information to the receiver from another GNSS sensor.       *
-- *                                                                          *
-- * Message can be issued multiple times within one epoch to provide         *
-- * information for all signals/satellites being tracked.                    *
-- *                                                                          *
-- ****************************************************************************
--
DataRawSatRangeInfo ::= SEQUENCE {
    validityTime                    TimeStamp,
    numberOfMessages                Unsigned8,              -- Number of range messages to be reported this epoch (N)
    messageNumber                   Unsigned8,              -- Number of range message being reported (0 to N-1)
    wordPadding                     Pad12bits,
    navSolutionMode                 NavSolutionMode,
    signalRangeInfos                RawSignalRangeInfos
}

-- Shall include multiple SignalRangeInfo objects, one per signal per satellite in the
-- message
RawSignalRangeInfos ::= SEQUENCE {
    rawSignalRangeInfos             SEQUENCE (SIZE(0..65535)) OF SignalRangeInfo
}


-- ****************************************************************************
-- * Satellite Range Residuals                                                *
-- *                                                                          *
-- * Message name:    DataSatRangeResiduals                                   *
-- * Message ID:      6300                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message type is used to provide the residuals of the GNSS satellite *
-- * ranges for all satellites being tracked by the receiver.                 *
-- *                                                                          *
-- * Notes:                                                                   *
-- *                                                                          *
-- ****************************************************************************
--
DataSatRangeResiduals ::= SEQUENCE {
    validityTime                    TimeStamp,
    numberOfMessages                Unsigned8,              -- Number of corrected range messages to be reported this epoch (N)
    messageNumber                   Unsigned8,              -- Number of corrected range message being reported (0 to N-1)
    rangeResiduals                  RangeResiduals
}

RangeResiduals ::= SEQUENCE {
    rangeResiduals                  SEQUENCE (SIZE(0..65535)) OF SEQUENCE {
        signalID                        SignalID,
        satID                           SatID,
        rangeResidual                   IEEE754Sp,              -- metres
        rangeRateResidual               IEEE754Sp,              -- metres/second
        cN0                             IEEE754Sp               -- dB-Hz
    }
}


-- ****************************************************************************
-- * Satellites In View                                                       *
-- *                                                                          *
-- * Message name:    DataSatsInView                                          *
-- * Message ID:      6361                                                    *
-- * Message status:  Core                                                    *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message details the satellites in view.                             *
-- *                                                                          *
-- * Notes:                                                                   *
-- *                                                                          *
-- * The list contains all satellites as determined by the almanacs           *
-- * currently held in the receiver and does not necessarily mean they are    *
-- * being tracked by the receiver. Status information is also provided on    *
-- * each of the services from the satellites.                                *
-- *                                                                          *
-- * The message is sent in multiple, ordered blocks with only satellites     *
-- * from a single constellation in each block. The constellation ID is       *
-- * specified in the message head.                                           *
-- *                                                                          *
-- * The satsInUse boolean reported for each satellite indicates whether the  *
-- * satellite is being used to generate a navigation solution. If only the   *
-- * satellites in use are of interest, DataSatsInUse can be requested        *
-- * instead.                                                                 *
-- *                                                                          *
-- ****************************************************************************
--
DataSatsInView ::= SEQUENCE {
    validityTime                    TimeStamp,
    numberOfMessages                Unsigned8,              -- Number of messages to be reported this epoch (N)
    messageNumber                   Unsigned8,              -- Number of message being reported (0 to N-1)
    constellationID                 ConstellationID,
    satellitesInView                SatsInView
}

SatsInView ::= SEQUENCE {
    wordPadding                     Pad10bits,
    satsInView                      SEQUENCE (SIZE(0..63)) OF SEQUENCE {
        satID                           SatID,
        elevationAndAzimuthValid        BOOLEAN,
        satInUse                        BOOLEAN,
        wordPadding                     Pad14bits,
        satelliteElevation              IEEE754Sp,              -- degrees (-90.0 <= value <= +90.0)
        satelliteAzimuth                IEEE754Sp,              -- degrees (-180.0 <= value < +180.0)
        signalsInView                   SignalsInfo
    }
}

SignalsInfo ::= SEQUENCE {
    wordPadding                     Pad12bits,
    signalsInfo                     SEQUENCE (SIZE(0..15)) OF SEQUENCE {
        signalID                        SignalID,
        logicalTrackerID                LogicalTrackerID,
        cN0                             IEEE754Sp,              -- dB-Hz
        wordPadding                     Pad4bits,
        trackingState                   SatTrackingState,
        wordPadding1                    Pad5bits,
        satSignalHealth                 SatSignalHealth
    }
}

-- ****************************************************************************
-- * Satellites In View ECEF                                                  *
-- *                                                                          *
-- * Message name:    DataSatsInViewECEF                                      *
-- * Message ID:      6413                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message details the satellites in view.                             *
-- *                                                                          *
-- * Notes:                                                                   *
-- *                                                                          *
-- * The list contains all satellites as determined by the almanacs currently *
-- * held in the receiver and does not necessarily mean they are being        *
-- * tracked by the receiver. Status information is also provided on each of  *
-- * the services from the satellites.                                        *
-- *                                                                          *
-- * The message is sent in multiple, ordered blocks with only satellites     *
-- * from a single constellation in each block. The constellation ID is       *
-- * specified in the message head.                                           *
-- *                                                                          *
-- * The satsInUse boolean reported for each satellite indicates whether the  *
-- * satellite is being used to generate a navigation solution. If only the   *
-- * satellites in use are of interest, DataSatsInUseECEF can be requested    *
-- * instead.                                                                 *
-- *                                                                          *
-- * Position uses an ECEF coordinate system with the WGS-84 datum origin.    *
-- *                                                                          *
-- ****************************************************************************
--
DataSatsInViewECEF ::= SEQUENCE {
    validityTime                    TimeStamp,
    numberOfMessages                Unsigned8,              -- Number of messages to be reported this epoch (N)
    messageNumber                   Unsigned8,              -- Number of message being reported (0 to N-1)
    constellationID                 ConstellationID,
    satellitesInView                SatsInViewECEF
}

SatsInViewECEF ::= SEQUENCE {
    wordPadding                     Pad10bits,
    satsInView                      SEQUENCE (SIZE(0..63)) OF SEQUENCE {
        satID                           SatID,
        positionValid                   BOOLEAN,
        satInUse                        BOOLEAN,
        wordPadding                     Pad14bits,
        position                        PositionXYZ,
        signalsInView                   SignalsInfo
    }
}


-- ****************************************************************************
-- * Satellites In Use                                                        *
-- *                                                                          *
-- * Message name:    DataSatsInUse                                           *
-- * Message ID:      6318                                                    *
-- * Message status:  Core                                                    *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message details the satellites/signals used to generate a           *
-- * navigation solution.                                                     *
-- *                                                                          *
-- * Notes:                                                                   *
-- *                                                                          *
-- * The message is sent in multiple, ordered blocks with only satellites     *
-- * from a single constellation in each block. The constellation ID is       *
-- * specified in the message head.                                           *
-- *                                                                          *
-- * Satellites/signals rejected by RAIM will not be included in this         *
-- * message.                                                                 *
-- *                                                                          *
-- ****************************************************************************
--
DataSatsInUse ::= SEQUENCE {
    validityTime                    TimeStamp,
    numberOfMessages                Unsigned8,              -- Number of messages to be reported this epoch (N)
    messageNumber                   Unsigned8,              -- Number of message being reported (0 to N-1)
    constellationID                 ConstellationID,
    satellitesInUse                 SatsInUse
}

SatsInUse ::= SEQUENCE {
    wordPadding                     Pad10bits,
    satsInUse                       SEQUENCE (SIZE(0..63)) OF SEQUENCE {
        satID                           SatID,
        elevationAndAzimuthValid        BOOLEAN,
        wordPadding                     Pad15bits,
        satelliteElevation              IEEE754Sp,              -- degrees (-90.0 <= value <= +90.0)
        satelliteAzimuth                IEEE754Sp,              -- degrees (-180.0 <= value < +180.0)
        signalsInUse                    SignalsInfo
    }
}

-- ****************************************************************************
-- * Satellites In Use ECEF                                                   *
-- *                                                                          *
-- * Message name:    DataSatsInUseECEF                                       *
-- * Message ID:      6425                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message details the satellites/signals used to generate a           *
-- * navigation solution.                                                     *
-- *                                                                          *
-- * Notes:                                                                   *
-- *                                                                          *
-- * The message is sent in multiple, ordered blocks with only satellites     *
-- * from a single constellation in each block. The constellation ID is       *
-- * specified in the message head.                                           *
-- *                                                                          *
-- * Satellites/signals rejected by RAIM will not be included in this         *
-- * message.                                                                 *
-- *                                                                          *
-- * Position uses an ECEF coordinate system with the WGS-84 datum origin.    *
-- *                                                                          *
-- ****************************************************************************
--
DataSatsInUseECEF ::= SEQUENCE {
    validityTime                    TimeStamp,
    numberOfMessages                Unsigned8,              -- Number of messages to be reported this epoch (N)
    messageNumber                   Unsigned8,              -- Number of message being reported (0 to N-1)
    constellationID                 ConstellationID,
    satellitesInUse                 SatsInUseECEF
}

SatsInUseECEF ::= SEQUENCE {
    wordPadding                     Pad10bits,
    satsInUse                       SEQUENCE (SIZE(0..63)) OF SEQUENCE {
        satID                           SatID,
        positionValid                   BOOLEAN,
        wordPadding                     Pad15bits,
        position                        PositionXYZ,
        signalsInUse                    SignalsInfo
    }
}


-- ****************************************************************************
-- * Set Magnetic Variation Correction                                        *
-- *                                                                          *
-- * Message name:    DataMagVarCorrection                                    *
-- * Message ID:      6311                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message sets the magnetic variation correction to be used.          *
-- *                                                                          *
-- * Notes:                                                                   *
-- *                                                                          *
-- ****************************************************************************
--
DataMagVarCorrection ::= SEQUENCE {
    wordPadding                     Pad12bits,
    magneticCorrectionSource        MagneticVariationSource,
    magneticVariationValue          IEEE754Sp               -- degrees (-180.0 <= value < +180.0)
}


-- ****************************************************************************
-- * Set Magnetic Deviation Correction                                        *
-- *                                                                          *
-- * Message name:    DataMagDevCorrection                                    *
-- * Message ID:      6317                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message sets the magnetic deviation correction values to be used.   *
-- *                                                                          *
-- * Notes:                                                                   *
-- *                                                                          *
-- * The deviation values provided are applied evenly over the full 360       *
-- * degrees circle starting at 0 degrees magnetic. E.g. with                 *
-- * magDevCorrectionType set to magDevCorrectionTypeManual, a sequence of    *
-- * 36 deviationValues would define the deviation corrections from 0 to 350  *
-- * degrees in 10 degree intervals (i.e. at 0, 10, 20, ...., 340, 350).      *
-- *                                                                          *
-- * The widely used sense of MagDev corrections is utilised such that the    *
-- * relevant deviation value will be added to the measured magnetic sensor   *
-- * (compass) bearing to obtain a corrected magnetic bearing.                *
-- *                                                                          *
-- ****************************************************************************
--
DataMagDevCorrection ::= SEQUENCE {
    wordPadding                     Pad14bits,
    magDevCorrectionType            ENUMERATED {
        magDevCorrectionTypeAuto,                               -- Receiver to calculate and utilise its own MagDev corrections (if supported)
        magDevCorrectionTypeOff,                                -- Do not apply MagDev corrections - any deviation values supplied will be ignored
        magDevCorrectionTypeManual                              -- Use supplied deviation values
    },
    wordPadding2                    Pad9bits,
    deviationValues                 SEQUENCE (SIZE(0..72)) OF IEEE754Sp     -- See Notes
}


-- ****************************************************************************
-- * NMEA Encapsulated Message                                                *
-- *                                                                          *
-- * Message name:    DataNMEAMessage                                         *
-- * Message ID:      6264                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * Data message for encapsulated NMEA sentences.                            *
-- *                                                                          *
-- * Notes:                                                                   *
-- *                                                                          *
-- ****************************************************************************
--
DataNMEAMessage ::= SEQUENCE {
    validityTime                    TimeStamp,
    wordPadding                     Pad8bits,
    nmeaSentence                    SEQUENCE (SIZE(0..255)) OF MessageOctet
}


-- ****************************************************************************
-- * RTCM104 Encapsulated Message                                             *
-- *                                                                          *
-- * Message name:    DataRTCM104Message                                      *
-- * Message ID:      6292                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message is nominally for input but could also be an output data     *
-- * message.                                                                 *
-- *                                                                          *
-- * Notes:                                                                   *
-- *                                                                          *
-- ****************************************************************************
--
DataRTCM104Message ::= SEQUENCE {
    validityTime                    TimeStamp,
    wordPadding                     Pad15bits,
    rtcm104Message                  CHOICE {
        rtcm104V2Message                SEQUENCE {
            header                          SEQUENCE (SIZE(4)) OF RTCM104Word,
            wordPadding                     Pad11bits,
            payload                         SEQUENCE (SIZE(0..31)) OF RTCM104Word
        },
        rtcm104V3Message                SEQUENCE {
            minorVersion                    INTEGER (0..63),
            payload                         SEQUENCE (SIZE(0..1023)) OF MessageOctet,
            checksum                        OCTET STRING (SIZE(3))
        }
    }
}

RTCM104Word ::= OCTET STRING (SIZE(4))      -- RTCM 30 bit word occupies least significant 30 bits of 4 byte structure


-- ****************************************************************************
-- * Attitude                                                                 *
-- *                                                                          *
-- * Message name:    DataAttitude                                            *
-- * Message ID:      6434                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message provides the calculated attitude relative to the tangential *
-- * plane at the platform's position using the selected Datum.               *
-- *                                                                          *
-- * Notes:                                                                   *
-- *                                                                          *
-- * Roll is positive clockwise (right wing down) relative to the horizontal; *
-- * Pitch is positive nose up relative to the horizontal; Heading is wrt     *
-- * True North.                                                              *
-- *                                                                          *
-- * Data is only valid if the sensorsInUse flag has at least one bit set.    *
-- * The sensorsInUse flag bits should only be set for sensors used to        *
-- * generate the values in the message.                                      *
-- *                                                                          *
-- ****************************************************************************
--
DataAttitude ::= SEQUENCE {
    validityTime                    TimeStamp,
    rollAngle                       IEEE754Sp,              -- degrees (-180.0 <= value < +180.0)
    pitchAngle                      IEEE754Sp,              -- degrees (-90.0 <= value <= +90.0)
    headingAngleTrue                IEEE754Sp,              -- degrees wrt True North (0.0 <= value < +360.0)
    sensorsInUse                    SensorsInUse
}


-- ****************************************************************************
-- * Heading                                                                  *
-- *                                                                          *
-- * Message name:    DataHeading                                             *
-- * Message ID:      6346                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message provides the calculated heading.                            *
-- *                                                                          *
-- * Notes:                                                                   *
-- *                                                                          *
-- * Data is only valid if the sensorsInUse flag has at least one bit set.    *
-- * The sensorsInUse flag bits should only be set for sensors used to        *
-- * generate the values in the message.                                      *
-- *                                                                          *
-- * If no magnetic correction source is available then true and magnetic     *
-- * will be reported the same.                                               *
-- *                                                                          *
-- ****************************************************************************
--
DataHeading ::= SEQUENCE {
    validityTime                    TimeStamp,
    headingAngleTrue                IEEE754Sp,              -- degrees (0.0 <= value < +360.0)
    wordPadding                     Pad12bits,
    magneticCorrectionSource        MagneticVariationSource,
    headingAngleMagnetic            IEEE754Sp,              -- degrees (0.0 <= value < +360.0)
    sensorsInUse                    SensorsInUse
}


-- ****************************************************************************
-- * INU State Vector Input                                                   *
-- *                                                                          *
-- * Message name:    DataINUStateVectorInput                                 *
-- * Message ID:      6278                                                    *
-- * Message status:  Optional(2)                                             *
-- * Frequency:       Up to 100Hz (the actual input rate may be limited by    *
-- *                  the bandwidth of the host interface.)                   *
-- * Input/Output:    Input                                                   *
-- *~~~~~~~~~~~~~~~~~~~~~~~~~~~~~~~~~~~~~~~~~~~~~~~~~~~~~~~~~~~~~~~~~~~~~~~~~~*
-- * Short Description:                                                       *
-- *                                                                          *
-- * This is a scaled version of the message DataLegacyINUStateVectorInput    *
-- * (see description and references with the legacy message itself). It      *
-- * provides the same parameters, but as scaled SI units.                    *
-- *                                                                          *
-- * Notes:                                                                   *
-- *                                                                          *
-- * The X, Y, Z reference frame used is the aircraft body frame. X is out    *
-- * the nose, Y is out the right wing, and Z is out the belly of the         *
-- * aircraft.                                                                *
-- *                                                                          *
-- ****************************************************************************
--
DataINUStateVectorInput ::= SEQUENCE {
    inuModeWord                     INUMode,                -- INU Mode word
    velocityTimeTag                 IEEE754Sp,              -- Time interval since last 1PPS (in seconds)

    velocityX                       IEEE754Sp,              -- Platform X velocity (out the nose) in m/s
    velocityY                       IEEE754Sp,              -- Platform Y velocity (out the right wing) in m/s
    velocityZ                       IEEE754Sp,              -- Platform Z velocity (through the belly) in m/s

    azimuth                         IEEE754Sp,              -- Platform azimuth in degrees (positive is clockwise wrt North)
    roll                            IEEE754Sp,              -- Platform roll in degrees (positive is starboard wing down)
    pitch                           IEEE754Sp,              -- Platform pitch in degrees (positive is up)

    presentTrueHeading              IEEE754Sp,              -- Heading in degrees wrt True North
    presentMagneticHeading          IEEE754Sp,              -- Heading in degrees wrt Magnetic North

    accelerationX                   IEEE754Sp,              -- Platform X acceleration (out the nose) in m/s/s
    accelerationY                   IEEE754Sp,              -- Platform Y acceleration (out the right wing) in m/s/s
    accelerationZ                   IEEE754Sp,              -- Platform Z acceleration (through the belly) in m/s/s

    cNEXx                           IEEE754Dp,              -- CNEX X value
    cNEXy                           IEEE754Dp,              -- CNEX Y value
    cNEXz                           IEEE754Dp,              -- CNEX Z value

    longitude                       IEEE754Dp,              -- in degrees, positive is East of Greenwich Meridian

    inertialAltitude                IEEE754Sp,              -- in metres referenced to the geoid of the selected datum (default is WGS-84)
    greatCircleSteeringError        IEEE754Sp,              -- in degrees
    xAxisResidualTilt               IEEE754Sp,              -- in degrees
    yAxisResidualTilt               IEEE754Sp,              -- in degrees

    inuModeWord2                    INUMode2,               -- INU Mode word II

    rollRate                        IEEE754Sp,              -- in degrees per second, positive is starboard wing down
    pitchRate                       IEEE754Sp,              -- in degrees per second, positive is nose up
    yawRate                         IEEE754Sp               -- in degrees per second, positive is yaw to the right
}


-- ****************************************************************************
-- * LEGACY INU State Vector Input                                            *
-- *                                                                          *
-- * Message name:    DataLegacyINUStateVectorInput                           *
-- * Message ID:      6422                                                    *
-- * Message status:  Optional(2)                                             *
-- * Frequency:       Up to 100Hz (the actual input rate may be limited by    *
-- *                  the bandwidth of the host interface.)                   *
-- * Input/Output:    Input                                                   *
-- *~~~~~~~~~~~~~~~~~~~~~~~~~~~~~~~~~~~~~~~~~~~~~~~~~~~~~~~~~~~~~~~~~~~~~~~~~~*
-- * Short Description:                                                       *
-- *                                                                          *
-- * THIS IS A LEGACY MESSAGE.  The definition here is to achieve backwards   *
-- * compatibility.                                                           *
-- *                                                                          *
-- * Notes:                                                                   *
-- *                                                                          *
-- * This message must be provided to the GNSS sensor at a minimum rate of    *
-- * 4Hz to enable INU aiding of the GNSS sensor. Further aiding data is      *
-- * used at no greater rate than 100Hz. This message should be used in       *
-- * conjunction with the INU Correction Data Input message.                  *
-- *                                                                          *
-- * This message was originally defined in: Aeronautical Systems Division,   *
-- * Air Force Systems Command, 'Specification for USAF Standard Form, Fit    *
-- * and Function Medium Accuracy Inertial Navigation Unit', SNU84-1,         *
-- * Revision D, 21 Sep 92, Message Block ID IO1/IO5.                         *
-- * Note Words IO1/IO5-02 through IO1/IO5-13 are identical to IO6/IO8-02     *
-- * through IO6/IO8-13.                                                      *
-- * Reference: https://apps.dtic.mil/dtic/tr/fulltext/u2/a332939.pdf         *
-- *                                                                          *
-- * The X, Y, Z reference frame used is the aircraft body frame. X is out    *
-- * the nose, Y is out the right wing, and Z is out the belly of the         *
-- * aircraft.                                                                *
-- *                                                                          *
-- ****************************************************************************
--
DataLegacyINUStateVectorInput ::= SEQUENCE {
    -- IO1/IO5 - 01: INU Mode word
    inuModeWord                     INUMode,
    -- IO6/IO8 - 02: Platform velocity time tag.
    -- Time from last 1PPS.
    -- LSB is 64 microseconds.
    velocityTimeTag                 Unsigned16,
    -- IO6/IO8 - 3(MSP), IO6/IO8 - 4(LSP): Platform velocity in X direction
    -- X is out the nose.
    -- An integer multiple of 3.81470E-6 (LSB=2^-18) feet per second (fps)
    velocityX                       SNU84Int32,
    -- IO6/IO8 - 5(MSP), IO6/IO8 - 6(LSP): Platform velocity in Y direction.
    -- Y is out the right wing.
    -- An integer multiple of 3.81470E-6 (LSB=2^-18) feet per second (fps)
    velocityY                       SNU84Int32,
    -- IO6/IO8 - 7(MSP), IO6/IO8 - 8(LSP): Platform velocity in Z direction.
    -- Z is out the belly of the aircraft.
    -- An integer multiple of 3.81470E-6 (LSB=2^-18) feet per second (fps)
    velocityZ                       SNU84Int32,
    -- IO6/IO8 - 9: Platform azimuth.
    -- Positive is clockwise with respect to True/Magnetic North.
    -- An integer multiple of 3.05176E-05 (LSB=2^-15) semi-circles
    platformAzimuth                 SNU84Int16,
    -- IO6/IO8 - 10: Platform roll.
    -- Positive is roll to starboard (starboard wing down).
    -- An integer multiple of 3.05176E-05 (LSB=2^-15) semi-circles
    roll                            SNU84Int16,
    -- IO6/IO8 - 11: Platform pitch.
    -- Positive is nose up.
    -- An integer multiple of 3.05176E-05 (LSB=2^-15) semi-circles
    pitch                           SNU84Int16,
    -- IO6/IO8 - 12: Present True heading.
    -- Positive is clockwise with respect to True North,
    -- An integer multiple of 3.05176E-05 (LSB=2^-15) semi-circles
    presentTrueHeading              SNU84Int16,
    -- IO6/IO8 - 13: Present Magnetic heading.
    -- Positive is clockwise with respect to Magnetic North
    -- An integer multiple of 3.05176E-05 (LSB=2^-15) semi-circles
    presentMagneticHeading          SNU84Int16,
    -- IO1 - 14: Platform X Acceleration
    -- An integer multiple of 0.03125 (LSB=2^-5) feet per second per second
    accelerationX                   SNU84Int16,
    -- IO1 - 15: Platform Y Acceleration
    -- An integer multiple of 0.03125 (LSB=2^-5) feet per second per second
    accelerationY                   SNU84Int16,
    -- IO1 - 16: Platform Z Acceleration
    -- An integer multiple of 0.03125 (LSB=2^-5) feet per second per second
    accelerationZ                   SNU84Int16,
    -- IO1 - 17(MSP), IO1 - 18(LSP): CNEX x value.
    -- An integer multiple of 9.31323E-10 (LSB=2^-30)
    cNEXx                           SNU84Int32,
    -- IO1 - 19(MSP), IO1 - 20(LSP): CNEX y value.
    -- An integer multiple of 9.31323E-10 (LSB=2^-30)
    cNEXy                           SNU84Int32,
    -- IO1 - 21(MSP), IO1 - 22(LSP: CNEX z value.
    -- An integer multiple of 9.31323E-10 (LSB=2^-30)
    cNEXz                           SNU84Int32,
    -- IO1 - 23(MSP), IO1 - 24(LSP): Longitude
    -- Positive is East; zero is Greenwich Meridian.
    -- INU latitude of the host platform in WGS-84.
    -- An integer multiple of 4.65661E-10 (LSB=2^-31) semi-circles
    longitude                       SNU84Int32,
    -- IO1 - 25: Inertial Altitude
    -- Referenced to the geoid of the selected datum (default is WGS-84)
    -- An integer multiple of 4.0 (LSB=2^2) feet
    inertialAltitude                SNU84Int16,
    -- IO1 - 26: Great Circle steering error.
    -- An integer multiple of 3.05175E-05 (LSB=2^-15) semi-circles
    greatCircleSteeringError        SNU84Int16,
    -- IO1 - 27: Platform x-axis residual tilt.
    -- An integer multiple of 1 arc second
    xAxisResidualTilt               SNU84Int16,
    -- IO1 - 28: Platform y-axis residual tilt.
    -- An integer multiple of 1 arc second
    yAxisResidualTilt               SNU84Int16,
    -- IO1 - 29: INU Mode word II
    inuModeWord2                    INUMode,
    -- IO1 - 30: Platform roll rate.
    -- Positive is roll to the right (starboard wing down).
    -- An integer multiple of 1.22070E-04 (LSB=2^-13) semi-circles per second
    rollRate                        SNU84Int16,
    -- IO1 - 31: Platform pitch rate.
    -- Positive is nose up, units are degrees per second.
    -- An integer multiple of 1.22070E-04 (LSB=2^-13) semi-circles per second
    pitchRate                       SNU84Int16,
    -- IO1 - 32: Platform yaw rate.
    -- Positive is yaw to the right (starboard).
    -- An integer multiple of 1.22070E-04 (LSB=2^-13) semi-circles per second
    yawRate                         SNU84Int16
}

-- A signed 16 bit integer.
-- This is a legacy type that is for use in legacy messages
SNU84Int16 ::= SEQUENCE {
    -- Sign Bit, FALSE (0) is positive
    sign                           BOOLEAN,
    -- Value, 15 bits.
    value                          INTEGER (0..32767)
}

-- A signed 32 bit integer.
-- This is a legacy type that is for use in legacy messages
SNU84Int32 ::= SEQUENCE {
    sign                            BOOLEAN,                -- Sign Bit, FALSE (0) is positive
    value                           INTEGER (0..2147483646) -- Value, 31 bits.
}

-- INU Mode word
INUMode ::= SEQUENCE {
    inertialSensorReferenceFail     BOOLEAN,                -- inertial sensor / reference has failed
    anyNavigationDataFail           BOOLEAN,                -- Any navigation data has failed
    degradedNavigation              BOOLEAN,                -- Navigation is degraded
    navigationDataUnavailable       BOOLEAN,                -- Navigation data is unavailable
    digitalAttitudeDataFail         BOOLEAN,                -- Attitude data failure
    degradedNAVReady                BOOLEAN,                -- Degraded navigation data is available
    attitudeReady                   BOOLEAN,                -- Attitude data available
    controlVectorAcknowledge        BOOLEAN,                -- Acknowledge control vector
    altitudeLoopBit                 BOOLEAN,                -- TBD
    inuInInitiatedBit               BOOLEAN,                -- TBD
    mechanizationFlag               BOOLEAN,                -- TBD
    inManualMagneticVariation       BOOLEAN,                -- TBD
    digitalSelect                   BOOLEAN,                -- TBD
    inGridMode                      BOOLEAN,                -- In Grid mode
    cDUFail                         BOOLEAN,                -- CDU has failed
    logicZero                       BOOLEAN                 -- set to false
}


-- INU Mode word 2
INUMode2 ::= SEQUENCE {
    off                             BOOLEAN,                -- Off
    standby                         BOOLEAN,                -- Standby
    airAlign                        BOOLEAN,                -- Air Align
    storedHeadingAlign              BOOLEAN,                -- Stored Air Align
    gcAlign                         BOOLEAN,                -- GC Align
    enhancedGCAlignReserved         BOOLEAN,                -- Enhanced GC Align (Reserved)
    precisionGCAlignReserved        BOOLEAN,                -- Precision GC Align (Reserved)
    eiaReserved                     BOOLEAN,                -- EIA (Reserved)
    navigate                        BOOLEAN,                -- Navigate
    overfly                         BOOLEAN,                -- Overfly
    auxiliary                       BOOLEAN,                -- Auxiliary
    orientBoresight                 BOOLEAN,                -- Orient/Boresight
    attitude                        BOOLEAN,                -- Attitude
    test                            BOOLEAN,                -- Test
    calibrateReserved               BOOLEAN,                -- Calibrate (Reserved)
    spare                           BOOLEAN                 -- Spare
}


-- ****************************************************************************
-- * INU Correction Data Input                                                *
-- *                                                                          *
-- * Message name:    DataINUCorrectionDataInput                              *
-- * Message ID:      6343                                                    *
-- * Message status:  Optional(2)                                             *
-- * Frequency:       As required                                             *
-- * Input/Output:    Input                                                   *
-- *~~~~~~~~~~~~~~~~~~~~~~~~~~~~~~~~~~~~~~~~~~~~~~~~~~~~~~~~~~~~~~~~~~~~~~~~~~*
-- * Short Description:                                                       *
-- *                                                                          *
-- * This message is sent to the GNSS Sensor when very large corrections have *
-- * been made to the INU and the new INU data following the reset is         *
-- * substantially different from the previously received data contained in   *
-- * the INU State Vector Message.                                            *
-- *                                                                          *
-- * Notes:                                                                   *
-- *                                                                          *
-- ****************************************************************************
--
DataINUCorrectionDataInput ::= SEQUENCE {
    validityTime                    TimeStamp,
    -- Time Of Transmission: Time from last 1 pulse-per-second
    timeOfTransmission              IEEE754Sp,              -- seconds
    -- Counter: This field contains the value of a counter which is incremented
    -- each time the message is recomputed (i.e. each time a new correction message
    -- is provided).
    counter                         Unsigned16,
    mode                            INUCorrectionMode,
    positionCorrectionValid         BOOLEAN,
    referenceHeadingValid           BOOLEAN,
    velocityCorrectionValid         BOOLEAN,
    headingCorrectionValid          BOOLEAN,
    xAxisCorrectionValid            BOOLEAN,
    yAxisCorrectionValid            BOOLEAN,
    wordPadding                     Pad10bits,
    positionCorrection              PositionLLA,
    referenceHeading                IEEE754Sp,              -- degrees (0.0 <= value < +360.0)
    velocityCorrection              VelocityXYZ,
    headingCorrection               IEEE754Sp,              -- degrees (-180.0 <= value < +180.0)
    xAxisCorrection                 IEEE754Sp,              -- degrees (-90.0 < value < 90.0)
    yAxisCorrection                 IEEE754Sp               -- degrees (-90.0 < value < 90.0)
}


-- ****************************************************************************
-- * LEGACY INU Correction Data Input                                         *
-- *                                                                          *
-- * Message name:    DataLegacyINUCorrectionDataInput                        *
-- * Message ID:      6362                                                    *
-- * Message status:  Optional(2)                                             *
-- * Frequency:       As required                                             *
-- * Input/Output:    Input                                                   *
-- *~~~~~~~~~~~~~~~~~~~~~~~~~~~~~~~~~~~~~~~~~~~~~~~~~~~~~~~~~~~~~~~~~~~~~~~~~~*
-- * Short Description:                                                       *
-- *                                                                          *
-- * THIS IS A LEGACY MESSAGE.  The definition here is to achieve backwards   *
-- * compatibility.                                                           *
-- *                                                                          *
-- * Notes:                                                                   *
-- *                                                                          *
-- * This message is sent to the GNSS Sensor when very large corrections have *
-- * been made to the INU and the new INU data following the reset is         *
-- * substantially different from the previously received data contained in   *
-- * the INU State Vector Message.                                            *
-- *                                                                          *
-- ****************************************************************************
--
DataLegacyINUCorrectionDataInput ::= SEQUENCE {
    -- Time of transmission
    -- Time from last 1PPS.
    -- LSB is 2^6 microsecond
    timeOfTransmission              Unsigned16,
    -- Time of Validity
    -- Time from last 1PPS.
    -- LSB is 2^6 microsecond
    timeOfValidity                  Unsigned16,
    -- This field contains the value of a counter which is incremented
    -- each time the message is recomputed (i.e. each time a new correction
    -- message is provided).
    counter                         Unsigned16,
    modeWord                        INUCorrectionMode,      -- Mode word
    latitudeCorrection              SNU84Int32,             -- LSB is 2^-31 semi-circles
    longitudeCorrection             SNU84Int32,             -- LSB is 2^-31 semi-circles
    altitudeCorrection              SNU84Int16,             -- An integer multiple of 0.125 (LSB=2^-3) feet
    referenceHeading                SNU84Int16,             -- LSB is 2^15 semi-circles
    xVelocityCorrection             SNU84Int16,             -- An integer multiple of 0.25 (LSB=2^-2) feet per second (fps)
    yVelocityCorrection             SNU84Int16,             -- An integer multiple of 0.25 (LSB=2^-2) feet per second (fps)
    zVelocityCorrection             SNU84Int16,             -- An integer multiple of 0.25 (LSB=2^-2) feet per second (fps)
    headingCorrection               SNU84Int16,             -- LSB is 2^15 semi-circles
    xAxisCorrection                 SNU84Int16,             -- LSB is 2^-17 Radians
    yAxisCorrection                 SNU84Int16              -- LSB is 2^-17 Radians
}

-- Indication which corrections are valid
INUCorrectionMode ::= SEQUENCE {
    spare1                          BOOLEAN,                -- First bit is spare
    tiltCorrectionsValid            BOOLEAN,                -- Tilt correction valid.  TRUE = Valid
    headingCorrectionsValid         BOOLEAN,                -- Heading correction valid.  TRUE = Valid
    velocityCorrectionsValid        BOOLEAN,                -- Velocity correction valid.  TRUE = Valid
    positionCorrectionsValid        BOOLEAN,                -- Position correction valid.  TRUE = Valid
    spare                           Pad11bits               -- 11 bits are spare
}


-- ****************************************************************************
-- * Navigation Sensor Aiding Input                                           *
-- *                                                                          *
-- * Message name:    DataExtNavSensorInput                                   *
-- * Message ID:      6319                                                    *
-- * Message status:  Optional(2)                                             *
-- * Frequency:       Up to 100Hz (the actual input rate may be limited by    *
-- *                  the bandwidth of the host interface.)                   *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the data from a variety of auxiliary navigation    *
-- * sensors.                                                                 *
-- *                                                                          *
-- * Notes:                                                                   *
-- *                                                                          *
-- * Depending on the host platform's navigation suite all or a portion of    *
-- * the navigation sensor data within this will be populated. It is the      *
-- * responsibility of the Host platform's mission system to consolidate the  *
-- * sensor data into this message.                                           *
-- *                                                                          *
-- ****************************************************************************
--
DataExtNavSensorInput ::= SEQUENCE {
    validityTime                    TimeStamp,
    validityFlags                   NavSensorAidingMode,
    sensorsInUse                    SensorsInUse,
    positionLLA                     PositionLLA,            -- position (latitude, longitude and altitude (metres above ellipsoid))
    radAltitude                     IEEE754Sp,              -- radar altitude in metres (corrected to be height above selected geoid)
    baroAltitude                    IEEE754Sp,              -- barometric height in metres (with reference to selected geoid)
    trueSpeed                       IEEE754Sp,              -- metres/second
    velocityENU                     VelocityENU,
    heading                         AngularDir,             -- heading bearing and reference
    pitch                           IEEE754Sp,              -- degrees (-90.0 <= value <= +90.0), positive is nose up referenced to local frame
    roll                            IEEE754Sp,              -- degrees (-180.0 <= value < +180.0), positive is right wing down referenced to local frame
    velocityBodyXYZ                 VelocityXYZ             -- X: positive is toward the nose, Y: positive is toward the left wing, Z: positive is up
}


-- Padded to use 16 bits.
NavSensorAidingMode ::= SEQUENCE {
    tovValid                        BOOLEAN,                -- TRUE = Valid
    latLonValid                     BOOLEAN,                -- TRUE = Valid
    altValid                        BOOLEAN,                -- TRUE = Valid
    radAltitudeValid                BOOLEAN,                -- TRUE = Valid
    baroAltitudeValid               BOOLEAN,                -- TRUE = Valid
    trueSpeedValid                  BOOLEAN,                -- TRUE = Valid
    velocityENUValid                BOOLEAN,                -- TRUE = Valid
    headingValid                    BOOLEAN,                -- TRUE = Valid
    pitchRollValid                  BOOLEAN,                -- TRUE = Valid
    velocityXYZValid                BOOLEAN,                -- TRUE = Valid
    trueSpeedTypeIsGround           BOOLEAN,                -- TRUE = Ground, FALSE = Air
    headingTypeIsTrue               BOOLEAN,                -- TRUE = True North, FALSE = Magnetic North
    reservedBits                    Pad4bits
}


-- ****************************************************************************
-- * Mean Sea Level Pressure                                                  *
-- *                                                                          *
-- * Message name:    DataPressureMSL                                         *
-- * Message ID:      6338                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message specifies the current local MSL pressure reading to support *
-- * absolute height reporting above MSL from a local barometric sensor.      *
-- *                                                                          *
-- * Notes:                                                                   *
-- *                                                                          *
-- ****************************************************************************
--
DataPressureMSL ::= SEQUENCE {
    validityTime                    TimeStamp,
    pressureMSL                     IEEE754Sp               -- Mean Sea Level (MSL) pressure in Pascals
}


-- ****************************************************************************
-- * Raw Received GNSS Nav Page Symbols                                       *
-- *                                                                          *
-- * Message name:    DataRawNavPageSymbols                                   *
-- * Message ID:      6388                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message contains raw navigation data page symbols from a specific   *
-- * GNSS service and frequency.                                              *
-- *                                                                          *
-- * Notes:                                                                   *
-- *                                                                          *
-- * This message includes all the received page symbols, including on-board  *
-- * data if applicable (service specific) and CRC data. The data is          *
-- * provided as a sequence of confidence levels for each bit (to allow       *
-- * off-line soft decision processing if required).                          *
-- *                                                                          *
-- * Each symbol is expressed as a confidence value range 0 to 15. 0          *
-- * represents symbols most likely to be a '0' and 15 represents symbols     *
-- * most likely to be a '1'.                                                 *
-- *                                                                          *
-- * The 4 bit symbols are packed into the bytes most significant part        *
-- * first, in the order they are received in the page/frame.                 *
-- *                                                                          *
-- * The validityTime is TOW for the start of the page and is reported in the *
-- * applicable constellation time reference.                                 *
-- *                                                                          *
-- ****************************************************************************
--
DataRawNavPageSymbols ::= SEQUENCE {
    validityTime                    TimeStamp,
    gnssSignal                      SignalID,
    satID                           SatID,
    pageType                        Unsigned16,             -- Page type is service dependent
    wordPadding                     Pad6bits,
    rawNavDataPageSymbols           SEQUENCE (SIZE(0..512)) OF INTEGER (0..15)
}


-- ****************************************************************************
-- * Raw Received GNSS Nav Page Bits                                          *
-- *                                                                          *
-- * Message name:    DataRawNavPageBits                                      *
-- * Message ID:      6275                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message contains raw navigation data page bits from a specific GNSS *
-- * service and frequency.                                                   *
-- *                                                                          *
-- * Notes:                                                                   *
-- *                                                                          *
-- * This message includes all the received page bits, including on-board     *
-- * data if applicable (service specific) and CRC bits. The data is          *
-- * provided as a sequence of bits following decoding.                       *
-- *                                                                          *
-- * The raw data bits are packed into the MessageOctets most significant     *
-- * bit first down to least significant bit, in the order they are received  *
-- * in the page/frame. Any unused bits of the final MessageOctet are set to  *
-- * 0 and further padded with 0 bits, if necessary, to ensure an even        *
-- * number of MessageOctets are sent. The bitCount field indicates how many  *
-- * of the bits within the rawNavDataPageBits field are received data.       *
-- *                                                                          *
-- * The validityTime is TOW for the start of the page and is reported in the *
-- * applicable constellation time reference.                                 *
-- *                                                                          *
-- ****************************************************************************
--
DataRawNavPageBits ::= SEQUENCE {
    validityTime                    TimeStamp,
    gnssSignal                      SignalID,
    satID                           SatID,
    pageType                        Unsigned16,             -- Page type is service dependent
    wordPadding                     Pad6bits,
    bitCount                        INTEGER (0..512),       -- Number of valid bits in the rawNavDataPageBits field
    wordPadding1                    Pad9bits,
    rawNavDataPageBits              SEQUENCE (SIZE(0..64)) OF MessageOctet
}


-- ****************************************************************************
-- * Inter GNSS Time Broadcast                                                *
-- *                                                                          *
-- * Message name:    DataInterGNSSTimeBroadcast                              *
-- * Message ID:      6404                                                    *
-- * Message status:  Core                                                    *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message is a generic GNSS to GNSS System Time Conversion message    *
-- * that provides the broadcast parameters. For example Galileo broadcasts   *
-- * the offset between Galileo and GPS, whilst the modernised GPS            *
-- * (CNAV/CNAV2) broadcasts offsets to the Galileo and GLONASS.              *
-- *                                                                          *
-- * Notes:                                                                   *
-- *                                                                          *
-- * The signal indicates the source GNSS bands.                              *
-- *                                                                          *
-- * The offsetConstellationID indicates the GNSS that the offset is          *
-- * relative to. The rate of change of drift is only currently broadcast     *
-- * from the GPS CNAV/CNAV2 services and will be set to zero for other       *
-- * systems. The sense of the offset parameters is as per the broadcast      *
-- * source.                                                                  *
-- *                                                                          *
-- ****************************************************************************
--
DataInterGNSSTimeBroadcast ::= SEQUENCE {
    validityTime                    TimeStamp,
    wordPadding                     Pad10bits,
    interGNSSTimeOffsets            SEQUENCE (SIZE(0..63)) OF SEQUENCE {
        signal                          SignalID,               -- Source of broadcast
        offsetConstellationID           ConstellationID,        -- Constellation ID (see Notes)
        constantTerm                    IEEE754Sp,              -- Constant term of the polynomial describing the offset in seconds
        rateOfChangeOfOffset            IEEE754Sp,              -- First order term in seconds/second
        rateOfChangeOfDrift             IEEE754Sp,              -- Second order term in seconds/second/second
        referenceTimeForGGTOData        Unsigned16,             -- seconds
        weekNumberOfGGTOReference       Unsigned16              -- weeks
    }
}


-- ****************************************************************************
-- * Inter GNSS Time Estimate                                                 *
-- *                                                                          *
-- * Message name:    DataInterGNSSTimeEstimate                               *
-- * Message ID:      6411                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message provides the polynomial parameters, as calculated by the    *
-- * receiver, required to estimate the time difference, and accuracy,        *
-- * between the offset Constellation and the reference Constellation.        *
-- *                                                                          *
-- * Notes:                                                                   *
-- *                                                                          *
-- * The message reports the required values for a sequence of constellation  *
-- * pairs.                                                                   *
-- *                                                                          *
-- * The offset is calculated using a first order polynomial to give the      *
-- * time interval between top-of-the-second marks for the                    *
-- * offsetConstellationID and the referenceConstellationID.                  *
-- *                                                                          *
-- * T_offset = T_reference + constantTerm + deltaT x rateOfChangeOfOffset    *
-- *                                                                          *
-- * The user should account separately for any bulk time differences         *
-- * between the GNSS reported times, such as leap seconds or time zone       *
-- * differences (e.g. for GLONASS time).                                     *
-- *                                                                          *
-- ****************************************************************************
--
DataInterGNSSTimeEstimate ::= SEQUENCE {
    validityTime                    TimeStamp,
    wordPadding                     Pad10bits,
    interGNSSTimeOffsets            SEQUENCE (SIZE(0..45)) OF SEQUENCE {
        referenceConstellationID        ConstellationID,
        offsetConstellationID           ConstellationID,
        constantTerm                    IEEE754Sp,              -- constant term of the polynomial describing the offset (seconds)
        rateOfChangeOfOffset            IEEE754Sp,              -- first order term (seconds/second)
        estimatedTimeOffsetAccuracy     IEEE754Sp,              -- seconds (1 sigma accuracy)
        estimatedTimeRateAccuracy       IEEE754Sp               -- seconds (1 sigma accuracy)
    }
}


-- ****************************************************************************
-- * Satellite/Signals Health                                                 *
-- *                                                                          *
-- * Message name:    DataSatSignalsHealth                                    *
-- * Message ID:      6309                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains a summary of the satellite/signal health.          *
-- *                                                                          *
-- * Notes:                                                                   *
-- *                                                                          *
-- * This message can be used to obtain information about satellite and       *
-- * signal health. This message can also be used to pass Health information  *
-- * to the receiver from an external source.                                 *
-- *                                                                          *
-- * The Navigational health of the satellite is given plus the health of     *
-- * each individual signal.                                                  *
-- *                                                                          *
-- ****************************************************************************
--
DataSatSignalsHealth ::= SEQUENCE {
    validityTime                    TimeStamp,
    wordPadding                     Pad8bits,
    satSignalsHealth                SatSignalsHealth        -- Signals Health
}

SatSignalsHealth ::= SEQUENCE (SIZE(0..255)) OF SEQUENCE {
    satID                           SatID,                  -- SatID within the Constellation (as indicated in signalID)
    satelliteHealth                 Unsigned16,             -- Satellite Navigational health (0 OK)
    wordPadding                     Pad12bits,
    signalsHealth                   SignalsHealth           -- Health of the given signals
}

SignalsHealth ::= SEQUENCE (SIZE(0..15)) OF SEQUENCE {
    signalID                        SignalID,
    wordPadding                     Pad13bits,
    satSignalHealth                 SatSignalHealth
}


-- Almanac Messages --
--
-- These messages provide the unscaled and scaled almanac.
-- The GNSSs provide different information so undertake on a constellation,
-- by constellation basis.
--
-- ****************************************************************************
-- * GPS Unscaled Almanac                                                     *
-- *                                                                          *
-- * Message name:    DataGPSUnscaledAlmanac                                  *
-- * Message ID:      6451                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the unscaled almanac parameters received from the  *
-- * tracked GPS satellites.                                                  *
-- *                                                                          *
-- * Notes:                                                                   *
-- *                                                                          *
-- * Note that the signal ID refers to where the message has come from.       *
-- * Units, scaling factors, and other semantic information (e.g. reference   *
-- * angles) for the various parameters can be found in:                      *
-- * Interface Specification NAVSTAR GPS.                                     *
-- *                                                                          *
-- ****************************************************************************
--
DataGPSUnscaledAlmanac ::= SEQUENCE {
    validityTime                    TimeStamp,
    numberOfMessages                Unsigned8,              -- Number of messages to report almanac
    messageNumber                   Unsigned8,              -- Number of message being reported (0 to N-1)
    dataSource                      DataSource,
    signalID                        GPSMultiSignalID,
    perSatAlmanacData               GPSSatUnscaledAlmanacs
}

GPSSatUnscaledAlmanacs ::= SEQUENCE {
    wordPadding                     Pad10bits,
    gpsSatUnscaledAlmanacs  SEQUENCE (SIZE(0..63)) OF SEQUENCE {
        wordPadding                     Pad13bits,
-- Choices 1 to 8 sent as 0 to 7 down the wire.
-- Padded to use 3 bits.
        data                            CHOICE {
            lnav                            GPSLNAVSatUnscaledAlmanacs,
            cnav                            GPSCNAVSatUnscaledMidiAlmanacs,
            cnav2                           GPSCNAVSatUnscaledMidiAlmanacs,
            reserved3                       GPSCNAVSatUnscaledMidiAlmanacs,     -- CNAV structure used as placeholder
            reserved4                       GPSCNAVSatUnscaledMidiAlmanacs,     -- CNAV structure used as placeholder
            reserved5                       GPSCNAVSatUnscaledMidiAlmanacs,     -- CNAV structure used as placeholder
            reserved6                       GPSCNAVSatUnscaledMidiAlmanacs,     -- CNAV structure used as placeholder
            reserved7                       GPSCNAVSatUnscaledMidiAlmanacs      -- CNAV structure used as placeholder
        }
    }
}

-- Comment states value of least significant bit, if not 1, and units.
GPSLNAVSatUnscaledAlmanacs ::= SEQUENCE {
    satID                           SatID,
    almanacReferenceTime            Unsigned8,              -- 2^12 seconds
    almanacReferenceWeekNumber      Unsigned8,              -- GPS week number modulo 256
    rootA                           Unsigned24,             -- 2^-11 sqrt(metres)
    ecc                             Unsigned16,             -- 2^-21 (dimensionless)
    deltaI                          Signed16,               -- 2^-19 semi-circles
    omega0                          Signed24,               -- 2^-23 semi-circles
    omegaDot                        Signed16,               -- 2^-38 semi-circles/second
    omega                           Signed24,               -- 2^-23 semi-circles
    m0                              Signed24,               -- 2^-23 semi-circles
    af0                             Signed11,               -- 2^-20 seconds
    af1                             Signed11,               -- 2^-38 seconds/second
    navDataHealthStatus             Unsigned3,
    signalHealthStatus              Unsigned5,
    wordPadding2                    Pad2bits
}

-- Comment states value of least significant bit, if not 1, and units.
GPSCNAVSatUnscaledMidiAlmanacs ::= SEQUENCE {
    satID                           SatID,
    almanacReferenceTime            Unsigned8,              -- 2^12 seconds
    almanacReferenceWeekNumber      Unsigned13,             -- GPS week number modulo 8192
    rootA                           Unsigned17,             -- 2^-4 sqrt(metres)
    ecc                             Unsigned11,             -- 2^-16 dimensionless
    deltaI                          Signed11,               -- 2^-11 semi-circles
    omega0                          Signed16,               -- 2^-15 semi-circles
    omegaDot                        Signed11,               -- 2^-33 semi-circles/second
    omega                           Signed16,               -- 2^-15 semi-circles
    m0                              Signed16,               -- 2^-15 semi-circles
    af0                             Signed11,               -- 2^-20 seconds
    af1                             Signed10,               -- 2^-37 seconds/second
    l1HealthStatus                  BOOLEAN,
    l2HealthStatus                  BOOLEAN,
    l5HealthStatus                  BOOLEAN,
    wordPadding2                    Pad1bits
}


-- ****************************************************************************
-- * GPS Scaled Almanac                                                       *
-- *                                                                          *
-- * Message name:    DataGPSScaledAlmanac                                    *
-- * Message ID:      6312                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the scaled almanac parameters received from the    *
-- * tracked GPS satellites.                                                  *
-- *                                                                          *
-- * Notes:                                                                   *
-- *                                                                          *
-- * Note that the signal ID refers to where the message has come from.       *
-- * Units, scaling factors, and other semantic information (e.g. reference   *
-- * angles) for the various parameters can be found in:                      *
-- * Interface Specification NAVSTAR GPS.                                     *
-- *                                                                          *
-- ****************************************************************************
--
DataGPSScaledAlmanac ::= SEQUENCE {
    validityTime                    TimeStamp,
    numberOfMessages                Unsigned8,              -- Number of messages to report almanac
    messageNumber                   Unsigned8,              -- Number of message being reported (0 to N-1)
    dataSource                      DataSource,
    signalID                        GPSMultiSignalID,
    perSatAlmanacData               GPSSatScaledAlmanacs
}

GPSSatScaledAlmanacs ::= SEQUENCE {
    wordPadding                     Pad10bits,
    gpsSatScaledAlmanacs  SEQUENCE (SIZE(0..63)) OF SEQUENCE {
        wordPadding                     Pad13bits,
-- Choices 1 to 8 sent as 0 to 7 down the wire.
-- Padded to use 3 bits.
        data                            CHOICE {
            lnav                            GPSLNAVSatScaledAlmanacs,
            cnav                            GPSCNAVSatScaledAlmanacs,
            cnav2                           GPSCNAVSatScaledAlmanacs,
            reserved3                       GPSCNAVSatScaledAlmanacs,   -- CNAV structure used as placeholder
            reserved4                       GPSCNAVSatScaledAlmanacs,   -- CNAV structure used as placeholder
            reserved5                       GPSCNAVSatScaledAlmanacs,   -- CNAV structure used as placeholder
            reserved6                       GPSCNAVSatScaledAlmanacs,   -- CNAV structure used as placeholder
            reserved7                       GPSCNAVSatScaledAlmanacs    -- CNAV structure used as placeholder
        }
    }
}

GPSLNAVSatScaledAlmanacs ::= SEQUENCE {
    satID                           SatID,
    wordPadding                     Pad12bits,
    almanacReferenceTime            INTEGER (0..602112),    -- seconds
    wordPadding1                    Pad8bits,
    almanacReferenceWeekNumber      INTEGER (0..255),       -- GPS week number modulo 256
    rootA                           IEEE754Sp,              -- sqrt(metres)
    ecc                             IEEE754Sp,              -- dimensionless
    deltaI                          IEEE754Sp,              -- radians
    omega0                          IEEE754Sp,              -- radians
    omegaDot                        IEEE754Sp,              -- radians/second
    omega                           IEEE754Sp,              -- radians
    m0                              IEEE754Sp,              -- radians
    af0                             IEEE754Sp,              -- seconds
    af1                             IEEE754Sp,              -- seconds/second
    wordPadding2                    Pad5bits,
    navDataHealthStatus             Unsigned3,
    wordPadding3                    Pad3bits,
    signalHealthStatus              Unsigned5
}

GPSCNAVSatScaledAlmanacs ::= SEQUENCE {
    satID                           SatID,
    wordPadding                     Pad12bits,
    almanacReferenceTime            INTEGER (0..602112),    -- seconds
    wordPadding1                    Pad3bits,
    almanacReferenceWeekNumber      INTEGER (0..8191),      -- GPS week number modulo 8192
    rootA                           IEEE754Sp,              -- sqrt(metres)
    ecc                             IEEE754Sp,              -- dimensionless
    deltaI                          IEEE754Sp,              -- radians
    omega0                          IEEE754Sp,              -- radians
    omegaDot                        IEEE754Sp,              -- radians/second
    omega                           IEEE754Sp,              -- radians
    m0                              IEEE754Sp,              -- radians
    af0                             IEEE754Sp,              -- seconds
    af1                             IEEE754Sp,              -- seconds/second
    l1HealthStatus                  BOOLEAN,
    l2HealthStatus                  BOOLEAN,
    l5HealthStatus                  BOOLEAN,
    wordPadding2                    Pad13bits
}


-- ****************************************************************************
-- * Galileo Unscaled Almanac                                                 *
-- *                                                                          *
-- * Message name:    DataGalUnscaledAlmanac                                  *
-- * Message ID:      6372                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the unscaled almanac parameters received from the  *
-- * tracked Galileo satellites.                                              *
-- *                                                                          *
-- * Notes:                                                                   *
-- *                                                                          *
-- * For the Galileo almanac, for the majority of decoded parameters, these   *
-- * are common across the navigation messages F/NAV and I/NAV.               *
-- *                                                                          *
-- * Note that the signal ID refers to where the message has come from.       *
-- * Units, scaling factors, and other semantic information (e.g. reference   *
-- * angles) for the various parameters can be found in:                      *
-- * Galileo Open Service Signal-in-Space Interface Control Document.         *
-- *                                                                          *
-- ****************************************************************************
--
DataGalUnscaledAlmanac ::= SEQUENCE {
    validityTime                    TimeStamp,
    numberOfMessages                Unsigned8,              -- Number of messages to report almanac
    messageNumber                   Unsigned8,              -- Number of message being reported (0 to N-1)
    dataSource                      DataSource,
    signalID                        GalMultiSignalID,
    perSatAlmanacData               GalSatUnscaledAlmanacs
}

GalSatUnscaledAlmanacs ::= SEQUENCE {
    wordPadding                     Pad10bits,
    galSatUnscaledAlmanacs  SEQUENCE (SIZE(0..63)) OF SEQUENCE {
        wordPadding                     Pad13bits,
-- Choices 1 to 8 sent as 0 to 7 down the wire.
-- Padded to use 3 bits.
        data                            CHOICE {
            fnav                            GalFNAVSatUnscaledAlmanacs,
            inav                            GalINAVSatUnscaledAlmanacs,
            reserved2                       GalINAVSatUnscaledAlmanacs,     -- I/NAV structure used as placeholder
            reserved3                       GalINAVSatUnscaledAlmanacs,     -- I/NAV structure used as placeholder
            reserved4                       GalINAVSatUnscaledAlmanacs,     -- I/NAV structure used as placeholder
            reserved5                       GalINAVSatUnscaledAlmanacs,     -- I/NAV structure used as placeholder
            reserved6                       GalINAVSatUnscaledAlmanacs,     -- I/NAV structure used as placeholder
            reserved7                       GalINAVSatUnscaledAlmanacs      -- I/NAV structure used as placeholder
        }
    }
}

-- Comment states value of least significant bit, if not 1, and units.
GalFNAVSatUnscaledAlmanacs ::= SEQUENCE {
    satID                           Unsigned6,
    almanacIOD                      Unsigned4,              -- dimensionless
    almanacReferenceTime            Unsigned10,             -- 600 seconds
    almanacReferenceWeekNumber      Unsigned2,              -- 1 week
    deltaRootA                      Signed13,               -- 2^-9 sqrt(metres)
    ecc                             Unsigned11,             -- 2^-16 dimensionless
    deltaI                          Signed11,               -- 2^-14 semi-circles
    omega0                          Signed16,               -- 2^-15 semi-circles
    omegaDot                        Signed11,               -- 2^-33 semi-circles/second
    omega                           Signed16,               -- 2^-15 semi-circles
    m0                              Signed16,               -- 2^-15 semi-circles
    af0                             Signed16,               -- 2^-19 seconds
    af1                             Signed13,               -- 2^-38 seconds/second
    e5aHealthStatus                 GalSignalHealthIndicator,
    wordPadding                     Pad13bits
}

-- Comment states value of least significant bit, if not 1, and units.
GalINAVSatUnscaledAlmanacs ::= SEQUENCE {
    satID                           Unsigned6,
    almanacIOD                      Unsigned4,              -- dimensionless
    almanacReferenceTime            Unsigned10,             -- 600 seconds
    almanacReferenceWeekNumber      Unsigned2,              -- 1 week
    deltaRootA                      Signed13,               -- 2^-9 sqrt(metres)
    ecc                             Unsigned11,             -- 2^-16 dimensionless
    deltaI                          Signed11,               -- 2^-14 semi-circles
    omega0                          Signed16,               -- 2^-15 semi-circles
    omegaDot                        Signed11,               -- 2^-33 semi-circles/second
    omega                           Signed16,               -- 2^-15 semi-circles
    m0                              Signed16,               -- 2^-15 semi-circles
    af0                             Signed16,               -- 2^-19 seconds
    af1                             Signed13,               -- 2^-38 seconds/second
    e1bHealthStatus                 GalSignalHealthIndicator,
    e5bHealthStatus                 GalSignalHealthIndicator,
    wordPadding                     Pad11bits
}


-- ****************************************************************************
-- * Galileo Scaled Almanac                                                   *
-- *                                                                          *
-- * Message name:    DataGalScaledAlmanac                                    *
-- * Message ID:      6392                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the scaled almanac parameters received from the    *
-- * tracked Galileo satellites.                                              *
-- *                                                                          *
-- * Notes:                                                                   *
-- *                                                                          *
-- * For the Galileo almanac, for the majority of decoded parameters, these   *
-- * are common across the navigation messages F/NAV and I/NAV.               *
-- *                                                                          *
-- * Note that the signal ID refers to where the message has come from.       *
-- * Units, scaling factors, and other semantic information (e.g. reference   *
-- * angles) for the various parameters can be found in:                      *
-- * Galileo Open Service Signal-in-Space Interface Control Document.         *
-- *                                                                          *
-- ****************************************************************************
--
DataGalScaledAlmanac ::= SEQUENCE {
    validityTime                    TimeStamp,
    numberOfMessages                Unsigned8,              -- Number of messages to report almanac
    messageNumber                   Unsigned8,              -- Number of message being reported (0 to N-1)
    dataSource                      DataSource,
    signalID                        GalMultiSignalID,
    perSatAlmanacData               GalSatScaledAlmanacs
}

GalSatScaledAlmanacs ::= SEQUENCE {
    wordPadding                     Pad10bits,
    galSatScaledAlmanacs  SEQUENCE (SIZE(0..63)) OF SEQUENCE {
        wordPadding                     Pad13bits,
-- Choices 1 to 8 sent as 0 to 7 down the wire.
-- Padded to use 3 bits.
        data                            CHOICE {
            fnav                            GalFNAVSatScaledAlmanacs,
            inav                            GalINAVSatScaledAlmanacs,
            reserved2                       GalINAVSatScaledAlmanacs,     -- I/NAV structure used as placeholder
            reserved3                       GalINAVSatScaledAlmanacs,     -- I/NAV structure used as placeholder
            reserved4                       GalINAVSatScaledAlmanacs,     -- I/NAV structure used as placeholder
            reserved5                       GalINAVSatScaledAlmanacs,     -- I/NAV structure used as placeholder
            reserved6                       GalINAVSatScaledAlmanacs,     -- I/NAV structure used as placeholder
            reserved7                       GalINAVSatScaledAlmanacs      -- I/NAV structure used as placeholder
        }
    }
}

GalFNAVSatScaledAlmanacs ::= SEQUENCE {
    satID                           SatID,
    wordPadding                     Pad12bits,
    almanacIOD                      Unsigned4,              -- dimensionless
    wordPadding1                    Pad12bits,
    almanacReferenceTime            INTEGER (0..613800),    -- seconds
    wordPadding2                    Pad14bits,
    almanacReferenceWeekNumber      Unsigned2,              -- weeks
    deltaRootA                      IEEE754Sp,              -- sqrt(metres)
    ecc                             IEEE754Sp,              -- dimensionless
    deltaI                          IEEE754Sp,              -- radians
    omega0                          IEEE754Sp,              -- radians
    omegaDot                        IEEE754Sp,              -- radians/second
    omega                           IEEE754Sp,              -- radians
    m0                              IEEE754Sp,              -- radians
    af0                             IEEE754Sp,              -- seconds
    af1                             IEEE754Sp,              -- seconds/second
    wordPadding3                    Pad14bits,
    e5aHealthStatus                 GalSignalHealthIndicator
}

GalINAVSatScaledAlmanacs ::= SEQUENCE {
    satID                           SatID,
    wordPadding                     Pad12bits,
    almanacIOD                      Unsigned4,              -- dimensionless
    wordPadding1                    Pad12bits,
    almanacReferenceTime            INTEGER (0..613800),    -- seconds
    wordPadding2                    Pad14bits,
    almanacReferenceWeekNumber      Unsigned2,              -- weeks
    deltaRootA                      IEEE754Sp,              -- sqrt(metres)
    ecc                             IEEE754Sp,              -- dimensionless
    deltaI                          IEEE754Sp,              -- radians
    omega0                          IEEE754Sp,              -- radians
    omegaDot                        IEEE754Sp,              -- radians/second
    omega                           IEEE754Sp,              -- radians
    m0                              IEEE754Sp,              -- radians
    af0                             IEEE754Sp,              -- seconds
    af1                             IEEE754Sp,              -- seconds/second
    wordPadding3                    Pad6bits,
    e1bHealthStatus                 GalSignalHealthIndicator,
    wordPadding4                    Pad6bits,
    e5bHealthStatus                 GalSignalHealthIndicator
}


-- ****************************************************************************
-- * BeiDou Unscaled Almanac                                                  *
-- *                                                                          *
-- * Message name:    DataBDSUnscaledAlmanac                                  *
-- * Message ID:      6327                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the unscaled almanac parameters received from the  *
-- * tracked BeiDou satellites.                                               *
-- *                                                                          *
-- * Notes:                                                                   *
-- *                                                                          *
-- * Note that the signal ID refers to where the message has come from.       *
-- * Units and scaling factors for the various parameters can be found in:    *
-- * BeiDou Navigation Satellite System Signal In Space ICD.                  *
-- *                                                                          *
-- ****************************************************************************
--
DataBDSUnscaledAlmanac ::= SEQUENCE {
    validityTime                    TimeStamp,
    numberOfMessages                Unsigned8,              -- Number of messages to report almanac
    messageNumber                   Unsigned8,              -- Number of message being reported (0 to N-1)
    dataSource                      DataSource,
    signalID                        BDSMultiSignalID,
    perSatAlmanacData               BDSSatUnscaledAlmanacs
}

BDSSatUnscaledAlmanacs ::= SEQUENCE {
    wordPadding                     Pad10bits,
    bdsSatUnscaledAlmanacs SEQUENCE (SIZE(0..63)) OF SEQUENCE {
        wordPadding                     Pad13bits,
-- Choices 1 to 8 sent as 0 to 7 down the wire.
-- Padded to use 3 bits.
        data                            CHOICE {
            dnav                            BDSDNAVSatUnscaledAlmanacs,
            cnav1                           BDSCNAVSatUnscaledMidiAlmanacs,
            cnav2                           BDSCNAVSatUnscaledMidiAlmanacs,
            reserved3                       BDSCNAVSatUnscaledMidiAlmanacs,     -- used as placeholder
            reserved4                       BDSCNAVSatUnscaledMidiAlmanacs,     -- used as placeholder
            reserved5                       BDSCNAVSatUnscaledMidiAlmanacs,     -- used as placeholder
            reserved6                       BDSCNAVSatUnscaledMidiAlmanacs,     -- used as placeholder
            reserved7                       BDSCNAVSatUnscaledMidiAlmanacs      -- used as placeholder
        }
    }
}

-- See Table 5.14, BeiDou Navigation Satellite System, SIS, ICD, Open Service Signal B1I (Version 3.0), February 2019
-- Comment states value of least significant bit, if not 1, and units
BDSDNAVSatUnscaledAlmanacs ::= SEQUENCE {
    satID                           SatID,
    almanacReferenceTime            Unsigned8,              -- 2^12 seconds
    rootA                           Unsigned24,             -- 2^-11 sqrt(metres)
    ecc                             Unsigned17,             -- 2^-21 dimensionless
    omega                           Signed24,               -- 2^-23 semi-circles
    m0                              Signed24,               -- 2^-23 semi-circles
    omega0                          Signed24,               -- 2^-23 semi-circles
    omegaDot                        Signed17,               -- 2^-38 semi-circles/second
    deltaI                          Signed16,               -- 2^-19 semi-circles
    a0                              Signed11,               -- 2^-20 seconds
    a1                              Signed11,               -- 2^-38 seconds/second
    almanacWeekNumber               Unsigned8,              -- weeks (BDT integer week count modulo 256)
    satHealthInfo                   Unsigned9,              -- bit flags
    wordPadding                     Pad15bits
}

-- See Table 7.13,  BeiDou Navigation Satellite System, SIS, ICD, Open Service Signal B2a (Version 1.0), December 2017
-- Comment states value of least significant bit, if not 1, and units
BDSCNAVSatUnscaledMidiAlmanacs ::= SEQUENCE {
    satID                           SatID,
    prn                             Unsigned6,              -- satellite PRN number
    satOrbitType                    Unsigned2,              -- 00: reserved, 01: GEO, 10: IGSO, 11: MEO
    almanacWeekNumber               Unsigned13,             -- weeks (BDT integer week count modulo 8192)
    almanacReferenceTime            Unsigned8,              -- 2^12 seconds
    ecc                             Unsigned11,             -- 2^-16 dimensionless
    deltaI                          Signed11,               -- 2^-14 semi-circles
    rootA                           Unsigned17,             -- 2^-4 sqrt(metres)
    omega0                          Signed16,               -- 2^-15 semi-circles
    omegaDot                        Signed11,               -- 2^-33 semi-circles/second
    omega                           Signed16,               -- 2^-15 semi-circles
    m0                              Signed16,               -- 2^-15 semi-circles
    af0                             Signed11,               -- 2^-20 seconds
    af1                             Signed10,               -- 2^-37 seconds/second
    satHealthInfo                   Unsigned8,              -- bit flags
    wordPadding                     Pad4bits
}


-- ****************************************************************************
-- * BDS Scaled Almanac                                                       *
-- *                                                                          *
-- * Message name:    DataBDSScaledAlmanac                                    *
-- * Message ID:      6405                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the scaled almanac parameters received from the    *
-- * tracked BeiDou satellites.                                               *
-- *                                                                          *
-- * Notes:                                                                   *
-- *                                                                          *
-- * Units and scaling factors for the various parameters can be found in:    *
-- * BeiDou Navigation Satellite System Signal In Space ICD.                  *
-- *                                                                          *
-- ****************************************************************************
--
DataBDSScaledAlmanac ::= SEQUENCE {
    validityTime                    TimeStamp,
    numberOfMessages                Unsigned8,              -- Number of messages to report almanac
    messageNumber                   Unsigned8,              -- Number of message being reported (0 to N-1)
    dataSource                      DataSource,
    signalID                        BDSMultiSignalID,
    perSatAlmanacData               BDSSatScaledAlmanacs
}

BDSSatScaledAlmanacs ::= SEQUENCE {
    wordPadding                     Pad10bits,
    bdsSatScaledAlmanacs SEQUENCE (SIZE(0..63)) OF SEQUENCE {
        wordPadding                     Pad13bits,
-- Choices 1 to 8 sent as 0 to 7 down the wire.
-- Padded to use 3 bits.
        data                            CHOICE {
            dnav                            BDSDNAVSatScaledAlmanacs,
            cnav1                           BDSCNAVSatScaledMidiAlmanacs,
            cnav2                           BDSCNAVSatScaledMidiAlmanacs,
            reserved3                       BDSCNAVSatScaledMidiAlmanacs,   -- used as placeholder
            reserved4                       BDSCNAVSatScaledMidiAlmanacs,   -- used as placeholder
            reserved5                       BDSCNAVSatScaledMidiAlmanacs,   -- used as placeholder
            reserved6                       BDSCNAVSatScaledMidiAlmanacs,   -- used as placeholder
            reserved7                       BDSCNAVSatScaledMidiAlmanacs    -- used as placeholder
        }
    }
}

-- See Table 5.14, BeiDou Navigation Satellite System, SIS, ICD, Open Service Signal B1I (Version 3.0), February 2019
-- Comment states value of least significant bit, if not 1, and units
BDSDNAVSatScaledAlmanacs ::= SEQUENCE {
    satID                           SatID,
    wordPadding                     Pad12bits,
    almanacReferenceTime            INTEGER (0..602112),    -- seconds
    rootA                           IEEE754Sp,              -- sqrt(metres)
    ecc                             IEEE754Sp,              -- dimensionless
    deltaI                          IEEE754Sp,              -- radians
    omega0                          IEEE754Sp,              -- radians
    omegaDot                        IEEE754Sp,              -- radians/second
    omega                           IEEE754Sp,              -- radians
    m0                              IEEE754Sp,              -- radians
    a0                              IEEE754Sp,              -- seconds
    a1                              IEEE754Sp,              -- seconds/second
    wordPadding1                    Pad8bits,
    almanacWeekNumber               INTEGER (0..255),       -- weeks (BDT integer week count modulo 256)
    wordPadding2                    Pad7bits,
    satHealthInfo                   Unsigned9               -- bit flags
}

-- See Table 7.13,  BeiDou Navigation Satellite System, SIS, ICD, Open Service Signal B2a (Version 1.0), December 2017
-- Comment states value of least significant bit, if not 1, and units
BDSCNAVSatScaledMidiAlmanacs ::= SEQUENCE {
    satID                           SatID,
    wordPadding                     Pad2bits,
    prn                             INTEGER (0..63),
    wordPadding1                    Pad6bits,
    satOrbitType                    Unsigned2,              -- 00: reserved, 01: GEO, 10: IGSO, 11: MEO
    wordPadding2                    Pad3bits,
    almanacWeekNumber               INTEGER (0..8191),      -- weeks (BDT integer week count modulo 8192)
    wordPadding3                    Pad12bits,
    almanacReferenceTime            INTEGER (0..602112),    -- seconds
    rootA                           IEEE754Sp,              -- sqrt(metres)
    ecc                             IEEE754Sp,              -- dimensionless
    deltaI                          IEEE754Sp,              -- radians
    omega0                          IEEE754Sp,              -- radians
    omegaDot                        IEEE754Sp,              -- radians/second
    omega                           IEEE754Sp,              -- radians
    m0                              IEEE754Sp,              -- radians
    af0                             IEEE754Sp,              -- seconds
    af1                             IEEE754Sp,              -- seconds/second
    wordPadding4                    Pad8bits,
    satHealthInfo                   Unsigned8               -- bit flags
}


-- ****************************************************************************
-- * GLONASS Unscaled Almanac                                                 *
-- *                                                                          *
-- * Message name:    DataGLOUnscaledAlmanac                                  *
-- * Message ID:      6447                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the unscaled almanac parameters received from the  *
-- * tracked GLONASS satellites.                                              *
-- *                                                                          *
-- * Notes:                                                                   *
-- *                                                                          *
-- * Note that the signal ID refers to where the message has come from.       *
-- * Units and scaling factors for the various parameters can be found in:    *
-- * GLONASS ICD.                                                             *
-- *                                                                          *
-- ****************************************************************************
--
DataGLOUnscaledAlmanac ::= SEQUENCE {
    validityTime                    TimeStamp,
    numberOfMessages                Unsigned8,              -- Number of messages to report almanac
    messageNumber                   Unsigned8,              -- Number of message being reported (0 to N-1)
    dataSource                      DataSource,
    signalID                        GLOMultiSignalID,
    perSatAlmanacData               GLOSatUnscaledAlmanacs
}

GLOSatUnscaledAlmanacs ::= SEQUENCE {
    wordPadding                     Pad10bits,
    gloSatUnscaledAlmanacs SEQUENCE (SIZE(0..63)) OF SEQUENCE {
        wordPadding                     Pad13bits,
-- Choices 1 to 8 sent as 0 to 7 down the wire.
-- Padded to use 3 bits.
        data                            CHOICE {
            fnav                            GLOFNAVSatUnscaledAlmanacs,
            fmnav                           GLOFMNAVSatUnscaledAlmanacs,
            cnav                            GLOCNAVSatUnscaledAlmanacs,
            reserved3                       GLOCNAVSatUnscaledAlmanacs,        -- used as placeholder
            reserved4                       GLOCNAVSatUnscaledAlmanacs,        -- used as placeholder
            reserved5                       GLOCNAVSatUnscaledAlmanacs,        -- used as placeholder
            reserved6                       GLOCNAVSatUnscaledAlmanacs,        -- used as placeholder
            reserved7                       GLOCNAVSatUnscaledAlmanacs         -- used as placeholder
        }
    }
}


-- See Table 4.9, ICD L1, L2 GLONASS, Edition 5.1 2008
-- Comment states value of least significant bit, if not 1, units and, optionally, (expected range)
GLOFNAVSatUnscaledAlmanacs ::= SEQUENCE {
    tauc                            Signed28,               -- 2^-27 seconds
    nDayA                           Unsigned11,             -- days (1-1461)
    nSatA                           Unsigned5,              -- dimensionless (1-24)
    hnA                             Unsigned5,              -- dimensionless (0-31)
    lambdaA                         Signed21,               -- 2^-20 semi-cycles
    tlambdaA                        Unsigned21,             -- 2^-5 seconds
    deltaiA                         Signed18,               -- 2^-20 semi-cycles
    deltaTA                         Signed22,               -- 2^-9 seconds per orbital period
    deltaTdotA                      Signed7,                -- 2^-14 seconds per orbital period ^ 2
    eccA                            Unsigned15,             -- 2^-20 dimensionless
    omegaA                          Signed16,               -- 2^-15 semi-cycles
    tauA                            Signed10,               -- 2^-18 seconds
    cA                              Unsigned1,              -- dimensionless (0-1)
    wordPadding                     Pad12bits
}


-- See Table 4.9, ICD L1, L2 GLONASS, Edition 5.1 2008
-- Comment states value of least significant bit, if not 1, units and, optionally, (expected range)
GLOFMNAVSatUnscaledAlmanacs ::= SEQUENCE {
    tauc                            Signed32,               -- 2^-31 seconds
    tauGPS                          Signed22,               -- 2^-30 days
    n4                              Unsigned5,              -- 4-year interval (1-31)
    nDayA                           Unsigned11,             -- days (1-1461)
    nSatA                           Unsigned5,              -- dimensionless (1-24)
    hnA                             Unsigned5,              -- dimensionless (0-31)
    lambdaA                         Signed21,               -- 2^-20 semi-cycles
    tlambdaA                        Unsigned21,             -- 2^-5 seconds
    deltaiA                         Signed18,               -- 2^-20 semi-cycles
    deltaTA                         Signed22,               -- 2^-9 seconds per orbital period
    deltaTdotA                      Signed7,                -- 2^-14 seconds per orbital period ^ 2
    eccA                            Unsigned15,             -- 2^-20 dimensionless
    omegaA                          Signed16,               -- 2^-15 semi-cycles
    mA                              Unsigned2,              -- dimensionless
    b1                              Signed11,               -- 2^-10 seconds
    b2                              Signed10,               -- 2^-16 seconds/msd
    kp                              Unsigned2,              -- dimensionless
    tauA                            Signed10,               -- 2^-18 seconds
    cA                              Unsigned1,              -- dimensionless (0-1)
    wordPadding                     Pad4bits
}

-- See string Type 20, GLONASS ICD, CDMA OS Navigation Signal L1 frequency band, Edition 1.0
-- and GLONASS ICD, CDMA OS Navigation Signal L3 frequency band, Edition 1.0
-- Comment states value of least significant bit, if not 1, units and, optionally, (expected range)
GLOCNAVSatUnscaledAlmanacs ::= SEQUENCE {
    jA                              Unsigned6,              -- SVN (0-63)
    to                              Unsigned2,              -- Orbit type (00)
    nS                              Unsigned6,              -- dimensionless (0-63)
    eA                              Unsigned6,              -- days (0-63)
    nDayA                           Unsigned11,             -- days (1-1461)
    srA                             Unsigned5,              -- dimensionless
    mA                              Unsigned3,              -- dimensionless
    tauA                            Signed14,               -- 2^-20 seconds
    lambdaA                         Signed21,               -- 2^-20 half-cycles
    tlambdaA                        Unsigned21,             -- 2^-5 seconds
    deltaiA                         Signed15,               -- 2^-20 half-cycles
    eccA                            Unsigned15,             -- 2^-20 dimensionless
    omegaA                          Signed16,               -- 2^-15 half-cycles
    deltaTA                         Signed19,               -- 2^-9 seconds
    deltaTdotA                      Signed7,                -- 2^-14 seconds per orbit
    wordPadding                     Pad9bits
}


-- ****************************************************************************
-- * GLONASS Scaled Almanac                                                   *
-- *                                                                          *
-- * Message name:    DataGLOScaledAlmanac                                    *
-- * Message ID:      6398                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the scaled almanac parameters received from the    *
-- * tracked GLONASS satellites.                                              *
-- *                                                                          *
-- * Notes:                                                                   *
-- *                                                                          *
-- * Note that the signal ID refers to where the message has come from.       *
-- * Units and scaling factors for the various parameters can be found in:    *
-- * GLONASS ICD.                                                             *
-- *                                                                          *
-- ****************************************************************************
--
DataGLOScaledAlmanac ::= SEQUENCE {
    validityTime                    TimeStamp,
    numberOfMessages                Unsigned8,              -- Number of messages to report almanac
    messageNumber                   Unsigned8,              -- Number of message being reported (0 to N-1)
    dataSource                      DataSource,
    signalID                        GLOMultiSignalID,
    perSatAlmanacData               GLOSatScaledAlmanacs
}

GLOSatScaledAlmanacs ::= SEQUENCE {
    wordPadding                     Pad10bits,
    gloSatScaledAlmanacs SEQUENCE (SIZE(0..63)) OF SEQUENCE {
        wordPadding                     Pad13bits,
-- Choices 1 to 8 sent as 0 to 7 down the wire.
-- Padded to use 3 bits.
        data                            CHOICE {
            fnav                            GLOFNAVSatScaledAlmanacs,
            fmnav                           GLOFMNAVSatScaledAlmanacs,
            cnav                            GLOCNAVSatScaledAlmanacs,
            reserved3                       GLOCNAVSatScaledAlmanacs,      -- used as placeholder
            reserved4                       GLOCNAVSatScaledAlmanacs,      -- used as placeholder
            reserved5                       GLOCNAVSatScaledAlmanacs,      -- used as placeholder
            reserved6                       GLOCNAVSatScaledAlmanacs,      -- used as placeholder
            reserved7                       GLOCNAVSatScaledAlmanacs       -- used as placeholder
        }
    }
}

-- See Table 4.9, ICD L1, L2 GLONASS, Edition 5.1 2008
-- Comment states units and, optionally, (expected range)
GLOFNAVSatScaledAlmanacs ::= SEQUENCE {
    tauc                            IEEE754Dp,              -- seconds
    wordPadding                     Pad5bits,
    nDayA                           INTEGER (0..1461),      -- days (1-1461)
    wordPadding1                    Pad11bits,
    nSatA                           INTEGER (0..24),        -- dimensionless (1-24)
    wordPadding2                    Pad11bits,
    hnA                             INTEGER (0..31),        -- dimensionless
    lambdaA                         IEEE754Sp,              -- semi-cycles
    tlambdaA                        IEEE754Sp,              -- seconds
    deltaiA                         IEEE754Sp,              -- semi-cycles
    deltaTA                         IEEE754Sp,              -- seconds per orbital period
    deltaTdotA                      IEEE754Sp,              -- seconds per orbital period ^ 2
    eccA                            IEEE754Sp,              -- dimensionless
    omegaA                          IEEE754Sp,              -- semi-cycles
    tauA                            IEEE754Sp,              -- seconds
    wordPadding3                    Pad15bits,
    cA                              Unsigned1               -- dimensionless (0-1)
}

-- See Table 4.9, ICD L1, L2 GLONASS, Edition 5.1 2008
-- Comment states units and, optionally, (expected range)
GLOFMNAVSatScaledAlmanacs ::= SEQUENCE {
    tauc                            IEEE754Dp,              -- seconds
    tauGPS                          IEEE754Sp,              -- seconds
    wordPadding                     Pad11bits,
    n4                              INTEGER (0..31),        -- 4-year interval (1-31)
    wordPadding1                    Pad5bits,
    nDayA                           INTEGER (0..1461),      -- days (1-1461)
    wordPadding2                    Pad11bits,
    nSatA                           INTEGER (0..24),        -- dimensionless (1-24)
    wordPadding3                    Pad11bits,
    hnA                             INTEGER (0..31),            -- dimensionless
    lambdaA                         IEEE754Sp,                  -- semi-cycles
    tlambdaA                        IEEE754Sp,              -- seconds
    deltaiA                         IEEE754Sp,              -- semi-cycles
    deltaTA                         IEEE754Sp,              -- seconds per orbital period
    deltaTdotA                      IEEE754Sp,              -- seconds per orbital period ^ 2
    eccA                            IEEE754Sp,              -- dimensionless
    omegaA                          IEEE754Sp,              -- semi-cycles
    b1                              IEEE754Sp,              -- seconds
    b2                              IEEE754Sp,              -- seconds/msd
    wordPadding4                    Pad6bits,
    mA                              Unsigned2,              -- dimensionless
    wordPadding5                    Pad6bits,
    kp                              Unsigned2,              -- dimensionless
    tauA                            IEEE754Sp,              -- seconds
    wordPadding6                    Pad15bits,
    cA                              Unsigned1               -- dimensionless (0-1)
}

-- See string Type 20, GLONASS ICD, CDMA OS Navigation Signal L1 frequency band, Edition 1.0
-- and GLONASS ICD, CDMA OS Navigation Signal L3 frequency band, Edition 1.0
-- Comment states units and, optionally, (expected range)
GLOCNAVSatScaledAlmanacs ::= SEQUENCE {
    satID                           SatID,                  -- SVN
    wordPadding                     Pad6bits,
    to                              INTEGER (0..3),         -- Orbit type (00)
    wordPadding1                    Pad2bits,
    nS                              INTEGER (0..63),        -- dimensionless (0-63)
    wordPadding2                    Pad2bits,
    eA                              INTEGER (0..63),        -- days (0-63)
    wordPadding3                    Pad13bits,
    nDayA                           INTEGER (0..1461),      -- days (1-1461)
    wordPadding4                    Pad3bits,
    srA                             INTEGER (0..31),        -- dimensionless
    wordPadding5                    Pad5bits,
    mA                              INTEGER (0..7),         -- dimensionless
    tauA                            IEEE754Sp,              -- seconds
    lambdaA                         IEEE754Sp,              -- half-cycles
    tlambdaA                        IEEE754Sp,              -- seconds
    deltaiA                         IEEE754Sp,              -- half-cycles
    eccA                            IEEE754Sp,              -- dimensionless
    omegaA                          IEEE754Sp,              -- half-cycles
    deltaTA                         IEEE754Sp,              -- seconds
    deltaTdotA                      IEEE754Sp               -- seconds per orbit
}


-- Ephemeris and clock corrections  --
--
-- These messages provide the unscaled and scaled ephemeris and clock
-- corrections.
-- The GNSSs provide different information so implement on a constellation
-- by constellation basis.
--
-- ****************************************************************************
-- * GPS Unscaled Ephemeris and Clock                                         *
-- *                                                                          *
-- * Message name:    DataGPSUnscaledEphemerisAndClock                        *
-- * Message ID:      6383                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains unscaled ephemeris and clock corrections for a     *
-- * single GPS satellite.                                                    *
-- *                                                                          *
-- * Notes:                                                                   *
-- *                                                                          *
-- * The message contents depends on the type of navigation message decoded.  *
-- * Units, scaling factors, and other semantic information (e.g. reference   *
-- * angles) for the various parameters can be found in:                      *
-- * Interface Specification NAVSTAR GPS.                                     *
-- *                                                                          *
-- ****************************************************************************
--
DataGPSUnscaledEphemerisAndClock ::= SEQUENCE {
    validityTime                    TimeStamp,
    dataSource                      DataSource,
    signal                          GPSMultiSignalID,
    satID                           SatID,
    wordPadding                     Pad13bits,
    gpsUnscaledEphemerisAndClock    GPSSatUnscaledEphemerisAndClock
}

-- Choices 1 to 8 sent as 0 to 7 down the wire.
-- Padded to use 3 bits.
GPSSatUnscaledEphemerisAndClock ::= CHOICE {
    lnav                            GPSLNAVSatUnscaledEphemerisAndClock,
    cnav                            GPSCNAVSatUnscaledEphemerisAndClock,
    reserved2                       GPSCNAVSatUnscaledEphemerisAndClock,    -- CNAV structure used as placeholder
    reserved3                       GPSCNAVSatUnscaledEphemerisAndClock,    -- CNAV structure used as placeholder
    reserved4                       GPSCNAVSatUnscaledEphemerisAndClock,    -- CNAV structure used as placeholder
    reserved5                       GPSCNAVSatUnscaledEphemerisAndClock,    -- CNAV structure used as placeholder
    reserved6                       GPSCNAVSatUnscaledEphemerisAndClock,    -- CNAV structure used as placeholder
    reserved7                       GPSCNAVSatUnscaledEphemerisAndClock     -- CNAV structure used as placeholder
}

-- Comment states value of least significant bit, if not 1, and units.
GPSLNAVSatUnscaledEphemerisAndClock ::= SEQUENCE {

    weekNumber                      Unsigned10,             -- weeks

    -- Signal Health Parameters
    navDataHealthStatusSummary      BOOLEAN,                -- as defined in IS-GPS-200
    signalHealthStatus              Unsigned5,              -- as defined in IS-GPS-200

    -- Clock Parameters
    clockIOD                        Unsigned10,             -- as defined in IS-GPS-200
    groupDelayDifferential          Signed8,                -- 2^-31 seconds
    clockReferenceTime              Unsigned16,             -- 2^4 seconds
    af2                             Signed8,                -- 2^-55 seconds/second/second
    af1                             Signed16,               -- 2^-43 seconds/second
    af0                             Signed22,               -- 2^-31 seconds

    -- Miscellaneous Parameters
    l2PDataFlag                     BOOLEAN,                -- as defined in IS-GPS-200
    codeOnL2                        Unsigned2,              -- as defined in IS-GPS-200
    userRangeAccuracy               Unsigned4,              -- as defined in IS-GPS-200
    wordPadding                     Pad1bits,

    -- Ephemeris Parameters
    ephemerisIOD                    Unsigned8,              -- as defined in IS-GPS-200
    crs                             Signed16,               -- 2^-5 metres
    deltaN                          Signed16,               -- 2^-43 semi-circles/second
    m0                              Signed32,               -- 2^-31 semi-circles
    cuc                             Signed16,               -- 2^-29 radians
    ecc                             Signed32,               -- 2^-33 dimensionless
    cus                             Signed16,               -- 2^-29 radians
    rootA                           Unsigned32,             -- 2^-19 sqrt(metres)
    ephemerisReferenceTime          Unsigned32,             -- 2^4 seconds
    cic                             Signed16,               -- 2^-29 radians
    omega0                          Signed32,               -- 2^-31 semi-circles
    cis                             Signed16,               -- 2^-29 radians
    i0                              Signed32,               -- 2^-31 semi-circles
    crc                             Signed16,               -- 2^-5 metres
    omega                           Signed32,               -- 2^-31 semi-circles
    omegaDot                        Signed24,               -- 2^-43 semi-circles/second
    iDot                            Signed14,               -- 2^-43 semi-circles/second
    wordPadding1                    Pad10bits
}

-- Comment states value of least significant bit, if not 1, and units.
GPSCNAVSatUnscaledEphemerisAndClock ::= SEQUENCE {

    ephemerisReferenceWeekNumber    Unsigned13,             -- weeks

    -- Signal Health Parameters
    l1HealthStatus                  BOOLEAN,                -- as defined in IS-GPS-200
    l2HealthStatus                  BOOLEAN,                -- as defined in IS-GPS-200
    l5HealthStatus                  BOOLEAN,                -- as defined in IS-GPS-200

    -- Ephemeris Parameters
    ceiDataSequencePropToW10        Unsigned11,             -- 300 seconds
    userRangeAccuracyED             Signed5,                -- as defined in IS-GPS-200
    ephemerisDataRefToW10           Unsigned11,             -- 300 seconds
    deltaA                          Signed26,               -- 2^-9 metres
    aDot                            Signed25,               -- 2^-21 metres/second
    deltaN                          Signed17,               -- 2^-44 semi-circles/second
    deltaNDot                       Signed23,               -- 2^-57 semi-circles/second/second
    m0                              Signed33,               -- 2^-32 semi-circles
    ecc                             Unsigned33,             -- 2^-34 dimensionless
    omega                           Signed33,               -- 2^-32 semi-circles
    ephemerisDataRefToW11           Unsigned11,             -- 300 seconds
    omega0                          Signed33,               -- 2^-32 semi-circles
    deltaOmegaDot                   Signed17,               -- 2^-44 semi-circles/second
    i0                              Signed33,               -- 2^-32 semi-circles
    iDot                            Signed15,               -- 2^-44 semi-circles/second
    cis                             Signed16,               -- 2^-30 radians
    cic                             Signed16,               -- 2^-30 radians
    crs                             Signed24,               -- 2^-8 meters
    crc                             Signed24,               -- 2^-8 meters
    cus                             Signed21,               -- 2^-30 radians
    cuc                             Signed21,               -- 2^-30 radians

    -- Clock Correction Parameters
    ceiDataSequencePropToW30        Unsigned11,             -- 300 seconds
    userRangeAccuracyNED0           Signed5,                -- as defined in IS-GPS-200
    userRangeAccuracyNED1           Unsigned3,              -- as defined in IS-GPS-200
    userRangeAccuracyNED2           Unsigned3,              -- as defined in IS-GPS-200
    clockReferenceTimeOfWeek        Unsigned11,             -- 300 seconds
    af0                             Signed26,               -- 2^-35 seconds
    af1                             Signed20,               -- 2^-48 seconds/second
    af2                             Signed10,               -- 2^-60 seconds/second/second

    -- Group Delay Parameters
    totalGroupDelay                 Signed13,               -- 2^-35 seconds
    interSignalCorrectionL1CA       Signed13,               -- 2^-35 seconds
    interSignalCorrectionL2C        Signed13,               -- 2^-35 seconds
    interSignalCorrectionL5I5       Signed13,               -- 2^-35 seconds
    interSignalCorrectionL5Q5       Signed13,               -- 2^-35 seconds

    wordPadding1                    Pad6bits

}


-- ****************************************************************************
-- * GPS Scaled Ephemeris and Clock                                           *
-- *                                                                          *
-- * Message name:    DataGPSScaledEphemerisAndClock                          *
-- * Message ID:      6322                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains scaled ephemeris and clock corrections for a       *
-- * single GPS satellite.                                                    *
-- *                                                                          *
-- * Notes:                                                                   *
-- *                                                                          *
-- * The message contents depends on the type of navigation message decoded.  *
-- * Units, scaling factors, and other semantic information (e.g. reference   *
-- * angles) for the various parameters can be found in:                      *
-- * Interface Specification NAVSTAR GPS.                                     *
-- *                                                                          *
-- ****************************************************************************
--
DataGPSScaledEphemerisAndClock ::= SEQUENCE {
    validityTime                    TimeStamp,
    dataSource                      DataSource,
    signal                          GPSMultiSignalID,
    satID                           SatID,
    wordPadding                     Pad13bits,
    gpsScaledEphemerisAndClock      GPSSatScaledEphemerisAndClock
}

-- Choices 1 to 8 sent as 0 to 7 down the wire.
-- Padded to use 3 bits.
GPSSatScaledEphemerisAndClock ::= CHOICE {
    lnav                            GPSLNAVSatScaledEphemerisAndClock,
    cnav                            GPSCNAVSatScaledEphemerisAndClock,
    reserved2                       GPSCNAVSatScaledEphemerisAndClock,   -- CNAV structure used as placeholder
    reserved3                       GPSCNAVSatScaledEphemerisAndClock,   -- CNAV structure used as placeholder
    reserved4                       GPSCNAVSatScaledEphemerisAndClock,   -- CNAV structure used as placeholder
    reserved5                       GPSCNAVSatScaledEphemerisAndClock,   -- CNAV structure used as placeholder
    reserved6                       GPSCNAVSatScaledEphemerisAndClock,   -- CNAV structure used as placeholder
    reserved7                       GPSCNAVSatScaledEphemerisAndClock    -- CNAV structure used as placeholder
}

GPSLNAVSatScaledEphemerisAndClock ::= SEQUENCE {

    -- Ephemeris Parameters
    ephemerisIOD                    Unsigned8,              -- as defined in IS-GPS-200
    wordPadding                     Pad4bits,
    userRangeAccuracy               Unsigned4,              -- as defined in IS-GPS-200
    wordPadding1                    Pad12bits,
    ephemerisReferenceTime          INTEGER (0..604784),    -- seconds
    wordPadding2                    Pad6bits,
    ephemerisReferenceWeekNumber    Unsigned10,             -- weeks
    m0                              IEEE754Dp,              -- radians
    deltaN                          IEEE754Sp,              -- radians/second
    ecc                             IEEE754Dp,              -- dimensionless
    rootA                           IEEE754Dp,              -- sqrt(metres)
    omega0                          IEEE754Dp,              -- radians
    i0                              IEEE754Dp,              -- radians
    omega                           IEEE754Dp,              -- radians
    omegaDot                        IEEE754Dp,              -- radians/second
    iDot                            IEEE754Sp,              -- radians/second
    cuc                             IEEE754Sp,              -- radians
    cus                             IEEE754Sp,              -- radians
    crc                             IEEE754Sp,              -- metres
    crs                             IEEE754Sp,              -- metres
    cic                             IEEE754Sp,              -- radians
    cis                             IEEE754Sp,              -- radians

    -- Clock Parameters
    wordPadding3                    Pad6bits,
    clockIOD                        Unsigned10,             -- as defined in IS-GPS-200
    wordPadding4                    Pad12bits,
    clockReferenceTime              INTEGER (0..604784),    -- seconds
    af2                             IEEE754Sp,              -- seconds/second/second
    af1                             IEEE754Sp,              -- seconds/second
    af0                             IEEE754Sp,              -- seconds

    -- Group Delay Parameters
    totalGroupDelay                 IEEE754Sp,              -- seconds

    -- Signal Health Parameters
    navDataHealthStatusSummary      BOOLEAN,                -- as defined in IS-GPS-200
    wordPadding5                    Pad10bits,
    signalHealthStatus              Unsigned5               -- as defined in IS-GPS-200
}

GPSCNAVSatScaledEphemerisAndClock ::= SEQUENCE {

    -- Ephemeris Parameters
    wordPadding                     Pad11bits,
    userRangeAccuracyED             Signed5,                -- as defined in IS-GPS-200
    wordPadding1                    Pad12bits,
    ephemerisReferenceTime          INTEGER (0..604500),    -- seconds
    wordPadding2                    Pad3bits,
    ephemerisReferenceWeekNumber    Unsigned13,             -- weeks
    wordPadding3                    Pad12bits,
    ephemerisDataPredictTimeOfWeek  INTEGER (0..604500),    -- seconds
    deltaA                          IEEE754Dp,              -- metres
    aDot                            IEEE754Dp,              -- metres/second
    deltaNDot                       IEEE754Sp,              -- radians/second/second
    m0                              IEEE754Dp,              -- radians
    ecc                             IEEE754Dp,              -- dimensionless
    omega                           IEEE754Dp,              -- radians
    omega0                          IEEE754Dp,              -- radians
    deltaOmegaDot                   IEEE754Sp,              -- radians/second
    i0                              IEEE754Dp,              -- radians
    iDot                            IEEE754Sp,              -- radians/second
    cis                             IEEE754Sp,              -- radians
    cic                             IEEE754Sp,              -- radians
    crs                             IEEE754Sp,              -- metres
    crc                             IEEE754Sp,              -- metres
    cus                             IEEE754Sp,              -- radians
    cuc                             IEEE754Sp,              -- radians

    -- Clock Correction Parameters
    wordPadding4                    Pad12bits,
    clockReferenceTime              INTEGER (0..604500),    -- seconds
    wordPadding5                    Pad12bits,
    clockDataPredictTimeOfWeek      INTEGER (0..604500),    -- seconds
    wordPadding6                    Pad3bits,
    userRangeAccuracyNED0           Signed5,                -- as defined in IS-GPS-200
    wordPadding7                    Pad5bits,
    userRangeAccuracyNED1           Unsigned3,              -- as defined in IS-GPS-200
    wordPadding8                    Pad5bits,
    userRangeAccuracyNED2           Unsigned3,              -- as defined in IS-GPS-200
    wordPadding9                    Pad8bits,
    af2                             IEEE754Sp,              -- seconds/second/second
    af1                             IEEE754Sp,              -- seconds/second
    af0                             IEEE754Dp,              -- seconds

    -- Group Delay Parameters
    totalGroupDelay                 IEEE754Sp,              -- seconds
    interSignalCorrectionL1CA       IEEE754Sp,              -- seconds
    interSignalCorrectionL2C        IEEE754Sp,              -- seconds
    interSignalCorrectionL5I5       IEEE754Sp,              -- seconds
    interSignalCorrectionL5Q5       IEEE754Sp,              -- seconds

    -- Signal Health Parameters
    l1HealthStatus                  BOOLEAN,                -- as defined in IS-GPS-200
    l2HealthStatus                  BOOLEAN,                -- as defined in IS-GPS-200
    l5HealthStatus                  BOOLEAN,                -- as defined in IS-GPS-200
    wordPadding10                   Pad13bits
}


-- ****************************************************************************
-- * Galileo Unscaled Ephemeris and Clock                                     *
-- *                                                                          *
-- * Message name:    DataGalUnscaledEphemerisAndClock                        *
-- * Message ID:      6328                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains unscaled ephemeris and clock corrections for a     *
-- * single Galileo satellite.                                                *
-- *                                                                          *
-- * Notes:                                                                   *
-- *                                                                          *
-- * The message contents depends on the type of navigation message decoded.  *
-- *                                                                          *
-- * Units, scaling factors, and other semantic information (e.g. reference   *
-- * angles) for the various parameters can be found in:                      *
-- * Galileo Open Service Signal-in-Space Interface Control Document.         *
-- * If parameters are decoded from an F/NAV message, clock parameters relate *
-- * to the dual frequency E1,E5a combination. If parameters are decoded from *
-- * an I/NAV message, clock parameters relate to the dual frequency E1,E5b   *
-- * combination.                                                             *
-- *                                                                          *
-- ****************************************************************************
--
DataGalUnscaledEphemerisAndClock ::= SEQUENCE {
    validityTime                    TimeStamp,
    dataSource                      DataSource,
    signal                          GalMultiSignalID,
    satID                           SatID,
    wordPadding                     Pad13bits,
    galUnscaledEphemerisAndClock    GalSatUnscaledEphemerisAndClock
}

-- Choices 1 to 8 sent as 0 to 7 down the wire.
-- Padded to use 3 bits.
GalSatUnscaledEphemerisAndClock ::= CHOICE {
    fnav                            GalFNAVSatUnscaledEphemerisAndClock,
    inav                            GalINAVSatUnscaledEphemerisAndClock,
    reserved2                       GalFNAVSatUnscaledEphemerisAndClock,    -- F/NAV structure used as placeholder
    reserved3                       GalFNAVSatUnscaledEphemerisAndClock,    -- F/NAV structure used as placeholder
    reserved4                       GalFNAVSatUnscaledEphemerisAndClock,    -- F/NAV structure used as placeholder
    reserved5                       GalFNAVSatUnscaledEphemerisAndClock,    -- F/NAV structure used as placeholder
    reserved6                       GalFNAVSatUnscaledEphemerisAndClock,    -- F/NAV structure used as placeholder
    reserved7                       GalFNAVSatUnscaledEphemerisAndClock     -- F/NAV structure used as placeholder
}

-- Comment states value of least significant bit, if not 1, and units.
GalFNAVSatUnscaledEphemerisAndClock ::= SEQUENCE {

    weekNumber                      Unsigned12,             -- weeks

    -- Issue of Data nav
    navIOD                          Unsigned10,             -- dimensionless

    -- Ephemeris parameters
    m0                              Signed32,               -- 2^-31 semi-circles
    deltaN                          Signed16,               -- 2^-43 semi-circles/second
    ecc                             Unsigned32,             -- 2^-33 dimensionless
    rootA                           Unsigned32,             -- 2^-19 sqrt(metres)
    omega0                          Signed32,               -- 2^-31 semi-circles
    i0                              Signed32,               -- 2^-31 semi-circles
    omega                           Signed32,               -- 2^-31 semi-circles
    omegaDot                        Signed24,               -- 2^-43 semi-circles/second
    iDot                            Signed14,               -- 2^-43 semi-circles/second
    cuc                             Signed16,               -- 2^-29 radians
    cus                             Signed16,               -- 2^-29 radians
    crc                             Signed16,               -- 2^-5 metres
    crs                             Signed16,               -- 2^-5 metres
    cic                             Signed16,               -- 2^-29 radians
    cis                             Signed16,               -- 2^-29 radians
    ephemerisReferenceTime          Unsigned14,             -- 60 seconds

    -- Clock Correction Parameters
    clockCorrectionReferenceToW     Unsigned14,             -- 60 seconds
    af0                             Signed31,               -- 2^-34 seconds
    af1                             Signed21,               -- 2^-46 seconds/second
    af2                             Signed6,                -- 2^-59 seconds/second/second

    signalInSpaceAccuracy           Unsigned8,

    -- Navigation Message (I/F) Dependent Parameters
    bgdE1E5a                        Unsigned10,             -- 2^-32 seconds
    e5aHealthStatus                 GalSignalHealthIndicator,
    e5aDataValidityStatus           BOOLEAN,                -- as defined in Galileo-OS-SIS-ICD
    wordPadding                     Pad9bits
}

-- Comment states value of least significant bit, if not 1, and units.
GalINAVSatUnscaledEphemerisAndClock ::= SEQUENCE {

    weekNumber                      Unsigned12,             -- weeks

    -- Issue of Data nav
    navIOD                          Unsigned10,             -- dimensionless

    -- Ephemeris parameters
    m0                              Signed32,               -- 2^-31 semi-circles
    deltaN                          Signed16,               -- 2^-43 semi-circles/second
    ecc                             Unsigned32,             -- 2^-33 dimensionless
    rootA                           Unsigned32,             -- 2^-19 sqrt(metres)
    omega0                          Signed32,               -- 2^-31 semi-circles
    i0                              Signed32,               -- 2^-31 semi-circles
    omega                           Signed32,               -- 2^-31 semi-circles
    omegaDot                        Signed24,               -- 2^-43 semi-circles/second
    iDot                            Signed14,               -- 2^-43 semi-circles/second
    cuc                             Signed16,               -- 2^-29 radians
    cus                             Signed16,               -- 2^-29 radians
    crc                             Signed16,               -- 2^-5 metres
    crs                             Signed16,               -- 2^-5 metres
    cic                             Signed16,               -- 2^-29 radians
    cis                             Signed16,               -- 2^-29 radians
    ephemerisReferenceTime          Unsigned14,             -- 60 seconds

    -- Clock Correction Parameters
    clockCorrectionReferenceToW     Unsigned14,             -- 60 seconds
    af0                             Signed31,               -- 2^-34 seconds
    af1                             Signed21,               -- 2^-46 seconds/second
    af2                             Signed6,                -- 2^-59 seconds/second/second

    signalInSpaceAccuracy           Unsigned8,

    -- Navigation Message (I/F) Dependent Parameters
    bgdE1E5b                        Unsigned10,             -- 2^-32 seconds
    e1bHealthStatus                 GalSignalHealthIndicator,
    e5bHealthStatus                 GalSignalHealthIndicator,
    e1bDataValidityStatus           BOOLEAN,                -- as defined in Galileo-OS-SIS-ICD
    e5bDataValidityStatus           BOOLEAN,                -- as defined in Galileo-OS-SIS-ICD
    wordPadding                     Pad6bits
}


-- ****************************************************************************
-- * Galileo Scaled Ephemeris and Clock                                       *
-- *                                                                          *
-- * Message name:    DataGalScaledEphemerisAndClock                          *
-- * Message ID:      6364                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains scaled ephemeris and clock corrections for a       *
-- * single Galileo satellite.                                                *
-- *                                                                          *
-- * Notes:                                                                   *
-- *                                                                          *
-- * The message contents depends on the type of navigation message decoded.  *
-- *                                                                          *
-- * Units, scaling factors, and other semantic information (e.g. reference   *
-- * angles) for the various parameters can be found in:                      *
-- * Galileo Open Service Signal-in-Space Interface Control Document.         *
-- * If parameters are decoded from an F/NAV message, clock parameters relate *
-- * to the dual frequency E1,E5a combination. If parameters are decoded from *
-- * an I/NAV message, clock parameters relate to the dual frequency E1,E5b   *
-- * combination.                                                             *
-- *                                                                          *
-- ****************************************************************************
--
DataGalScaledEphemerisAndClock ::= SEQUENCE {
    validityTime                    TimeStamp,
    dataSource                      DataSource,
    signal                          GalMultiSignalID,
    satID                           SatID,
    wordPadding                     Pad13bits,
    galDecodedEphemeris             GalSatScaledEphemerisAndClock
}

-- Choices 1 to 8 sent as 0 to 7 down the wire.
-- Padded to use 3 bits.
GalSatScaledEphemerisAndClock ::= CHOICE {
    fnav                            GalFNAVSatScaledEphemerisAndClock,
    inav                            GalINAVSatScaledEphemerisAndClock,
    reserved2                       GalFNAVSatScaledEphemerisAndClock,    -- F/NAV structure used as placeholder
    reserved3                       GalFNAVSatScaledEphemerisAndClock,    -- F/NAV structure used as placeholder
    reserved4                       GalFNAVSatScaledEphemerisAndClock,    -- F/NAV structure used as placeholder
    reserved5                       GalFNAVSatScaledEphemerisAndClock,    -- F/NAV structure used as placeholder
    reserved6                       GalFNAVSatScaledEphemerisAndClock,    -- F/NAV structure used as placeholder
    reserved7                       GalFNAVSatScaledEphemerisAndClock     -- F/NAV structure used as placeholder
}

GalFNAVSatScaledEphemerisAndClock ::= SEQUENCE {
    -- Issue of Data nav
    navIOD                          Unsigned16,             -- dimensionless

    -- Ephemeris parameters
    wordPadding                     Pad8bits,
    signalInSpaceAccuracy           Unsigned8,
    wordPadding1                    Pad12bits,
    ephemerisReferenceTime          INTEGER (0..982980),    -- seconds
    m0                              IEEE754Dp,              -- radians
    deltaN                          IEEE754Sp,              -- radians/second
    ecc                             IEEE754Dp,              -- dimensionless
    rootA                           IEEE754Dp,              -- sqrt(metres)
    omega0                          IEEE754Dp,              -- radians
    i0                              IEEE754Dp,              -- radians
    omega                           IEEE754Dp,              -- radians
    omegaDot                        IEEE754Sp,              -- radians/second
    iDot                            IEEE754Sp,              -- radians/second
    cuc                             IEEE754Sp,              -- radians
    cus                             IEEE754Sp,              -- radians
    crc                             IEEE754Sp,              -- metres
    crs                             IEEE754Sp,              -- metres
    cic                             IEEE754Sp,              -- radians
    cis                             IEEE754Sp,              -- radians

    -- Clock Parameters
    wordPadding2                    Pad12bits,
    clockReferenceTime              INTEGER (0..982980),    -- seconds
    af0                             IEEE754Dp,              -- seconds
    af1                             IEEE754Sp,              -- seconds/second
    af2                             IEEE754Sp,              -- seconds/second/second

    -- Navigation Message Dependent Parameters
    bgdE1E5a                        IEEE754Sp,              -- seconds
    wordPadding3                    Pad6bits,
    e5aHealthStatus                 GalSignalHealthIndicator,
    e5aDataValidityStatus           BOOLEAN,                -- as defined in Galileo-OS-SIS-ICD
    wordPadding4                    Pad7bits
}

GalINAVSatScaledEphemerisAndClock ::= SEQUENCE {
    -- Issue of Data nav
    navIOD                          Unsigned16,             -- dimensionless

    -- Ephemeris parameters
    wordPadding                     Pad8bits,
    signalInSpaceAccuracy           Unsigned8,
    wordPadding1                    Pad12bits,
    ephemerisReferenceTime          INTEGER (0..982980),    -- seconds
    m0                              IEEE754Dp,              -- radians
    deltaN                          IEEE754Sp,              -- radians/second
    ecc                             IEEE754Dp,              -- dimensionless
    rootA                           IEEE754Dp,              -- sqrt(metres)
    omega0                          IEEE754Dp,              -- radians
    i0                              IEEE754Dp,              -- radians
    omega                           IEEE754Dp,              -- radians
    omegaDot                        IEEE754Sp,              -- radians/second
    iDot                            IEEE754Sp,              -- radians/second
    cuc                             IEEE754Sp,              -- radians
    cus                             IEEE754Sp,              -- radians
    crc                             IEEE754Sp,              -- metres
    crs                             IEEE754Sp,              -- metres
    cic                             IEEE754Sp,              -- radians
    cis                             IEEE754Sp,              -- radians

    -- Clock Parameters
    wordPadding2                    Pad12bits,
    clockReferenceTime              INTEGER (0..982980),    -- seconds
    af0                             IEEE754Dp,              -- seconds
    af1                             IEEE754Sp,              -- seconds/second
    af2                             IEEE754Sp,              -- seconds/second/second

    -- Navigation Message Dependent Parameters
    bgdE1E5b                        IEEE754Sp,              -- seconds
    wordPadding3                    Pad4bits,
    e1bHealthStatus                 GalSignalHealthIndicator,
    e5bHealthStatus                 GalSignalHealthIndicator,
    e1bDataValidityStatus           BOOLEAN,                -- as defined in Galileo-OS-SIS-ICD
    e5bDataValidityStatus           BOOLEAN,                -- as defined in Galileo-OS-SIS-ICD
    wordPadding4                    Pad6bits
}


-- ****************************************************************************
-- * BeiDou Unscaled Ephemeris and Clock                                      *
-- *                                                                          *
-- * Message name:    DataBDSUnscaledEphemerisAndClock                        *
-- * Message ID:      6301                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains unscaled ephemeris and clock corrections for a     *
-- * single BeiDou satellite.                                                 *
-- *                                                                          *
-- * Notes:                                                                   *
-- *                                                                          *
-- * The message contents depends on the type of navigation message decoded.  *
-- * Units and scaling factors for the various parameters can be found in:    *
-- * BeiDou Navigation Satellite System Signal In Space ICD.                  *
-- *                                                                          *
-- ****************************************************************************
--
DataBDSUnscaledEphemerisAndClock ::= SEQUENCE {
    validityTime                    TimeStamp,
    dataSource                      DataSource,
    signal                          BDSMultiSignalID,
    satID                           SatID,
    wordPadding                     Pad13bits,
    bdsUnscaledEphemerisAndClock    BDSSatUnscaledEphemerisAndClock
}

-- Choices 1 to 8 sent as 0 to 7 down the wire.
-- Padded to use 3 bits.
BDSSatUnscaledEphemerisAndClock ::= CHOICE {
    dnav                            BDSDNAVSatUnscaledEphemerisAndClock,
    cnav1                           BDSCNAVSatUnscaledEphemerisAndClock,
    cnav2                           BDSCNAVSatUnscaledEphemerisAndClock,
    reserved3                       BDSCNAVSatUnscaledEphemerisAndClock,    -- used as placeholder
    reserved4                       BDSCNAVSatUnscaledEphemerisAndClock,    -- used as placeholder
    reserved5                       BDSCNAVSatUnscaledEphemerisAndClock,    -- used as placeholder
    reserved6                       BDSCNAVSatUnscaledEphemerisAndClock,    -- used as placeholder
    reserved7                       BDSCNAVSatUnscaledEphemerisAndClock     -- used as placeholder
}

-- See Tables 5.10 & 5.7, BeiDou Navigation Satellite System, SIS, ICD, Open Service Signal B1I (Version 3.0), February 2019
-- Comment states value of least significant bit, if not 1, and units
BDSDNAVSatUnscaledEphemerisAndClock ::= SEQUENCE {

    -- Ephemeris Parameters
    ephemerisAOD                    Unsigned5,              -- see reference
    ephemerisReferenceTime          Unsigned17,             -- 2^3 seconds
    rootA                           Unsigned32,             -- 2^-19 sqrt(metres)
    ecc                             Unsigned32,             -- 2^-33 dimensionless
    omega                           Signed32,               -- 2^-31 semi-circles
    deltaN                          Signed16,               -- 2^-43 semi-circles/second
    m0                              Signed32,               -- 2^-31 semi-circles
    omega0                          Signed32,               -- 2^-31 semi-circles
    omegaDot                        Signed24,               -- 2^-43 semi-circles/second
    i0                              Signed32,               -- 2^-31 semi-circles
    iDot                            Signed14,               -- 2^-43 semi-circles/second
    cuc                             Signed18,               -- 2^-31 radians
    cus                             Signed18,               -- 2^-31 radians
    crc                             Signed18,               -- 2^-6 metres
    crs                             Signed18,               -- 2^-6 metres
    cic                             Signed18,               -- 2^-31 radians
    cis                             Signed18,               -- 2^-31 radians

    -- Clock Parameters
    clockAOD                        Unsigned5,              -- see reference
    clockReferenceTime              Unsigned17,             -- 2^3 seconds
    a0                              Signed24,               -- 2^-33 seconds
    a1                              Signed22,               -- 2^-50 seconds/second
    a2                              Signed11,               -- 2^-66 seconds/second/second

    -- Group Delay Parameters
    tGD1                            Signed10,               -- 0.1 nano seconds
    tGD2                            Signed10,               -- 0.1 nano seconds

    -- Satellite Health Parameters
    satH1                           Unsigned1,              -- '0' means broadcasting satellite is good and '1' means not
    wordPadding                     Pad4bits
}

-- See Tables 7.7, 7.5, 7.6 and 7.22,  BeiDou Navigation Satellite System, SIS, ICD, Open Service Signal B2a (Version 1.0), December 2017
-- Comment states value of least significant bit, if not 1, and units
BDSCNAVSatUnscaledEphemerisAndClock ::= SEQUENCE {

   -- Ephemeris Parameters
    ephemerisIOD                    Unsigned8,              -- see reference
    ephemerisReferenceTime          Unsigned11,             -- 300 seconds
    satOrbitType                    Unsigned2,              -- 01 (1) indicates the GEO satellite, 10 (2) indicates the IGSO satellite, 11 (3) indicates the MEO satellite, and 00 (0) is reserved.
    deltaA                          Signed26,               -- 2^-9 metres
    aDot                            Signed25,               -- 2^-21 metres/second
    deltaN0                         Signed17,               -- 2^-44 semi-circles/second
    deltaN0Dot                      Signed23,               -- 2^-57 semi-circles/second/second
    m0                              Signed33,               -- 2^-32 semi-circles
    ecc                             Unsigned33,             -- 2^-34 dimensionless
    omega                           Signed33,               -- 2^-32 semi-circles
    omega0                          Signed33,               -- 2^-32 semi-circles
    i0                              Signed33,               -- 2^-32 semi-circles
    omegaDot                        Signed19,               -- 2^-44 semi-circles/second
    i0Dot                           Signed15,               -- 2^-44 semi-circles/second
    cis                             Signed16,               -- 2^-30 radians
    cic                             Signed16,               -- 2^-30 radians
    crs                             Signed24,               -- 2^-8 metres
    crc                             Signed24,               -- 2^-8 metres
    cus                             Signed21,               -- 2^-30 radians
    cuc                             Signed21,               -- 2^-30 radians

    -- Clock Correction Parameters
    clockIOD                        Unsigned10,             -- see reference
    clockReferenceTime              Unsigned11,             -- 300 seconds
    a0                              Signed25,               -- 2^-34 seconds
    a1                              Signed22,               -- 2^-50 seconds/second
    a2                              Signed11,               -- 2^-66 seconds/second/second

    -- Group Delay Parameters
    tGDB1Cp                         Signed12,               -- 2^-34 seconds
    tGDB2ap                         Signed12,               -- 2^-34 seconds
    iscB1Cd                         Signed12,               -- 2^-34 seconds

    -- Satellite Health Parameters
    satHealthStatus                 Unsigned2,              -- 0 - satellite is healthy, 1 - satellite is unhealthy or in test, 2 and 3 - reserved
    wordPadding                     Pad10bits
}


-- ****************************************************************************
-- * BeiDou Scaled Ephemeris and Clock                                        *
-- *                                                                          *
-- * Message name:    DataBDSScaledEphemerisAndClock                          *
-- * Message ID:      6256                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains scaled ephemeris and clock corrections for a       *
-- * single BeiDou satellite.                                                 *
-- *                                                                          *
-- * Notes:                                                                   *
-- *                                                                          *
-- * The message contents depends on the type of navigation message decoded.  *
-- * Units and scaling factors for the various parameters can be found in:    *
-- * BeiDou Navigation Satellite System Signal In Space ICD.                  *
-- *                                                                          *
-- ****************************************************************************
--
DataBDSScaledEphemerisAndClock ::= SEQUENCE {
    validityTime                    TimeStamp,
    dataSource                      DataSource,
    signal                          BDSMultiSignalID,
    satID                           SatID,
    wordPadding                     Pad13bits,
    bdsScaledEphemerisAndClock      BDSSatScaledEphemerisAndClock
}

-- Choices 1 to 8 sent as 0 to 7 down the wire.
-- Padded to use 3 bits.
BDSSatScaledEphemerisAndClock ::= CHOICE {
    dnav                            BDSDNAVSatScaledEphemerisAndClock,
    cnav1                           BDSCNAVSatScaledEphemerisAndClock,
    cnav2                           BDSCNAVSatScaledEphemerisAndClock,
    reserved3                       BDSCNAVSatScaledEphemerisAndClock,   -- used as placeholder
    reserved4                       BDSCNAVSatScaledEphemerisAndClock,   -- used as placeholder
    reserved5                       BDSCNAVSatScaledEphemerisAndClock,   -- used as placeholder
    reserved6                       BDSCNAVSatScaledEphemerisAndClock,   -- used as placeholder
    reserved7                       BDSCNAVSatScaledEphemerisAndClock    -- used as placeholder
}

-- See Tables 5.10 & 5.7, BeiDou Navigation Satellite System, SIS, ICD, Open Service Signal B1I (Version 3.0), February 2019
-- Comment states units
BDSDNAVSatScaledEphemerisAndClock ::= SEQUENCE {

    -- Ephemeris Parameters
    wordPadding                     Pad11bits,
    ephemerisAOD                    INTEGER (0..31),        -- see reference
    wordPadding1                    Pad12bits,
    ephemerisReferenceTime          INTEGER (0..604792),    -- seconds
    rootA                           IEEE754Dp,              -- sqrt(metres)
    ecc                             IEEE754Dp,              -- dimensionless
    omega                           IEEE754Dp,              -- radians
    deltaN                          IEEE754Sp,              -- radians/second
    m0                              IEEE754Dp,              -- radians
    omega0                          IEEE754Dp,              -- radians
    omegaDot                        IEEE754Sp,              -- radians/second
    i0                              IEEE754Dp,              -- radians
    iDot                            IEEE754Sp,              -- radians/second
    cuc                             IEEE754Sp,              -- radians
    cus                             IEEE754Sp,              -- radians
    crc                             IEEE754Sp,              -- metres
    crs                             IEEE754Sp,              -- metres
    cic                             IEEE754Sp,              -- radians
    cis                             IEEE754Sp,              -- radians

    -- Clock Parameters
    wordPadding2                    Pad11bits,
    clockAOD                        INTEGER (0..31),        -- see reference
    wordPadding3                    Pad12bits,
    clockReferenceTime              INTEGER (0..604792),    -- seconds
    a0                              IEEE754Sp,              -- seconds/second/second
    a1                              IEEE754Sp,              -- seconds/second
    a2                              IEEE754Sp,              -- seconds

    -- Group Delay Parameters
    tGD1                            IEEE754Sp,              -- seconds
    tGD2                            IEEE754Sp,              -- seconds

    -- Satellite Health Parameters
    satH1                           BOOLEAN,                -- '0' means broadcasting satellite is good and '1' means not
    wordPadding4                    Pad15bits
}

-- See Tables 7.7, 7.5, 7.6 and 7.22,  BeiDou Navigation Satellite System, SIS, ICD, Open Service Signal B2a (Version 1.0), December 2017
-- Comment states units
BDSCNAVSatScaledEphemerisAndClock ::= SEQUENCE {

    -- Ephemeris Parameters
    wordPadding                     Pad8bits,
    ephemerisIOD                    INTEGER (0..255),       -- see reference
    wordPadding1                    Pad12bits,
    ephemerisReferenceTime          INTEGER (0..604500),    -- seconds
    wordPadding2                    Pad14bits,
    satOrbitType                    INTEGER (0..3),         -- 01 (1) indicates the GEO satellite, 10 (2) indicates the IGSO satellite, 11 (3) indicates the MEO satellite, and 00 (0) is reserved.
    deltaA                          IEEE754Dp,              -- metres
    aDot                            IEEE754Dp,              -- metres/second
    deltaN0                         IEEE754Sp,              -- semi-circles/second
    deltaN0Dot                      IEEE754Sp,              -- semi-circles/second/second
    m0                              IEEE754Dp,              -- semi-circles
    ecc                             IEEE754Dp,              -- dimensionless
    omega                           IEEE754Dp,              -- semi-circles
    omega0                          IEEE754Dp,              -- semi-circles
    i0                              IEEE754Dp,              -- semi-circles
    omegaDot                        IEEE754Sp,              -- semi-circles/second
    i0Dot                           IEEE754Sp,              -- semi-circles/second
    cis                             IEEE754Sp,              -- radians
    cic                             IEEE754Sp,              -- radians
    crs                             IEEE754Sp,              -- metres
    crc                             IEEE754Sp,              -- metres
    cus                             IEEE754Sp,              -- radians
    cuc                             IEEE754Sp,              -- radians

    -- Clock Correction Parameters
    wordPadding3                    Pad6bits,
    clockIOD                        INTEGER (0..1023),      -- see reference
    clockReferenceTime              IEEE754Sp,              -- seconds
    a0                              IEEE754Dp,              -- seconds
    a1                              IEEE754Sp,              -- seconds/second
    a2                              IEEE754Sp,              -- seconds/second/second

    -- Group Delay Parameters
    tGDB1Cp                         IEEE754Sp,              -- seconds
    tGDB2ap                         IEEE754Sp,              -- seconds
    iscB1Cd                         IEEE754Sp,              -- seconds

    -- Satellite Health Parameters
    wordPadding4                    Pad14bits,
    satHealthStatus                 INTEGER (0..3)          -- 0 - satellite is healthy, 1 - satellite is unhealthy or in test, 2 and 3 - reserved
}


-- ****************************************************************************
-- * GLONASS Unscaled Ephemeris and Clock                                     *
-- *                                                                          *
-- * Message name:    DataGLOUnscaledEphemerisAndClock                        *
-- * Message ID:      6259                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains unscaled ephemeris and clock corrections for a     *
-- * single GLONASS satellite.                                                *
-- *                                                                          *
-- * Notes:                                                                   *
-- *                                                                          *
-- * Units and scaling factors for the various parameters can be found in:    *
-- * GLONASS ICD.                                                             *
-- * The message contents depends on the type of navigation message decoded.  *
-- *                                                                          *
-- ****************************************************************************
--
DataGLOUnscaledEphemerisAndClock ::= SEQUENCE {
    validityTime                    TimeStamp,
    dataSource                      DataSource,
    signal                          GLOMultiSignalID,
    satID                           SatID,
    wordPadding                     Pad13bits,
    gloUnscaledEphemerisAndClock    GLOSatUnscaledEphemerisAndClock
}

-- Choices 1 to 8 sent as 0 to 7 down the wire.
-- Padded to use 3 bits.
GLOSatUnscaledEphemerisAndClock ::= CHOICE {
    fnav                            GLOFNAVSatUnscaledEphemerisAndClock,
    fmnav                           GLOFMNAVSatUnscaledEphemerisAndClock,
    cnav                            GLOCNAVSatUnscaledEphemerisAndClock,
    reserved3                       GLOCNAVSatUnscaledEphemerisAndClock,    -- used as placeholder
    reserved4                       GLOCNAVSatUnscaledEphemerisAndClock,    -- used as placeholder
    reserved5                       GLOCNAVSatUnscaledEphemerisAndClock,    -- used as placeholder
    reserved6                       GLOCNAVSatUnscaledEphemerisAndClock,    -- used as placeholder
    reserved7                       GLOCNAVSatUnscaledEphemerisAndClock     -- used as placeholder
}

-- See Table 4.5, ICD L1, L2 GLONASS, Edition 5.1 2008
-- Comment states value of least significant bit, if not 1, units and, optionally, (expected range)
GLOFNAVSatUnscaledEphemerisAndClock ::= SEQUENCE {

   -- Clock Parameters
    tkh                             Unsigned5,              -- hours (0-23)
    tkm                             Unsigned6,              -- minutes (0-59)
    tks                             Unsigned1,              -- 30 seconds (0 or 30)
    tb                              Unsigned7,              -- 15 minutes (15-1425)
    gammantb                        Signed11,               -- 2^-40 dimensionless
    tauntb                          Signed22,               -- 2^-30 seconds

    -- Ephemeris Parameters
    xntb                            Signed27,               -- 2^-11 km
    yntb                            Signed27,               -- 2^-11 km
    zntb                            Signed27,               -- 2^-11 km
    xntbdot                         Signed24,               -- 2^-20 km/second
    yntbdot                         Signed24,               -- 2^-20 km/second
    zntbdot                         Signed24,               -- 2^-20 km/second
    xntbdotdot                      Signed5,                -- 2^-30 km/second/second
    yntbdotdot                      Signed5,                -- 2^-30 km/second/second
    zntbdotdot                      Signed5,                -- 2^-30 km/second/second

    -- Flags and Supplementary Parameters
    bn                              Unsigned3,              -- dimensionless
    deltataun                       Signed5,                -- 2^-30 seconds
    en                              Unsigned5,              -- days (0-31)
    p1                              Unsigned2,              -- dimensionless
    p2                              Unsigned1,              -- dimensionless
    p3                              Unsigned1,              -- dimensionless

    wordPadding                     Pad3bits
}

-- See Table 4.5, ICD L1, L2 GLONASS, Edition 5.1 2008
-- Comment states value of least significant bit, if not 1, units and, optionally, (expected range)
GLOFMNAVSatUnscaledEphemerisAndClock ::= SEQUENCE {

   -- Clock Parameters
    tkh                             Unsigned5,              -- hours (0-23)
    tkm                             Unsigned6,              -- minutes (0-59)
    tks                             Unsigned1,              -- 30 seconds (0 or 30)
    tb                              Unsigned7,              -- 15 minutes (15-1425)
    m                               Unsigned2,              -- dimensionless (0-3)
    gammantb                        Signed11,               -- 2^-40 dimensionless
    tauntb                          Signed22,               -- 2^-30 seconds

    -- Ephemeris Parameters
    xntb                            Signed27,               -- 2^-11 km
    yntb                            Signed27,               -- 2^-11 km
    zntb                            Signed27,               -- 2^-11 km
    xntbdot                         Signed24,               -- 2^-20 km/second
    yntbdot                         Signed24,               -- 2^-20 km/second
    zntbdot                         Signed24,               -- 2^-20 km/second
    xntbdotdot                      Signed5,                -- 2^-30 km/second/second
    yntbdotdot                      Signed5,                -- 2^-30 km/second/second
    zntbdotdot                      Signed5,                -- 2^-30 km/second/second

    -- Flags and Supplementary Parameters
    bn                              Unsigned3,              -- dimensionless
    p                               Unsigned2,              -- dimensionless
    nt                              Unsigned11,             -- days (0-1461)
    ft                              Unsigned4,              -- dimensionless
    n                               Unsigned5,              -- dimensionless (0-31)
    deltataun                       Signed5,                -- 2^-30 seconds
    en                              Unsigned5,              -- days (0-31)
    p1                              Unsigned2,              -- dimensionless
    p2                              Unsigned1,              -- dimensionless
    p3                              Unsigned1,              -- dimensionless
    p4                              Unsigned1,              -- dimensionless

    -- Satellite Health
    ln                              Unsigned1,              -- dimensionless (0 - healthy, 1 - malfunction)

    wordPadding                     Pad9bits
}

-- See string Type 10, 11 & 12, GLONASS ICD, CDMA OS Navigation Signal L1 frequency band, Edition 1.0
-- and GLONASS ICD, CDMA OS Navigation Signal L3 frequency band, Edition 1.0
-- Comment states value of least significant bit, if not 1, units and, optionally, (expected range)
GLOCNAVSatUnscaledEphemerisAndClock ::= SEQUENCE {

    -- Clock Correction Parameters
    n4                              Unsigned5,              -- 4 year interval (1-31)
    nT                              Unsigned11,             -- 24 hours (1-1461)
    mj                              Unsigned3,              -- dimensionless
    ps                              Unsigned6,              -- dimensionless (0-63)
    tb                              Unsigned10,             -- 90 seconds (0-86310)
    eEj                             Unsigned8,              -- 6 hours (1-255)
    eTj                             Unsigned8,              -- 6 hours (1-255)
    rEj                             Unsigned2,              -- dimensionless (0-3)
    rTj                             Unsigned2,              -- dimensionless (0-3)
    fEj                             Signed5,                -- dimensionless (-15-15)
    fTj                             Signed5,                -- dimensionless (-15-15)
    tauj                            Signed32,               -- 2^-38 seconds
    gammaj                          Signed19,               -- 2^-48 dimensionless
    betaj                           Signed15,               -- 2^-57 /second
    tauc                            Signed40,               -- 2^-31 seconds
    taucdot                         Signed13,               -- 2^-49 seconds/second
    deltataujL2                     Signed18,               -- 2^-38 seconds
    deltatauGPS                     Signed30,               -- 2^-38 seconds

    -- Ephemeris Parameters
    xj                              Signed40,               -- 2^-20 km
    yj                              Signed40,               -- 2^-20 km
    zj                              Signed40,               -- 2^-20 km
    xjdot                           Signed35,               -- 2^-30 km/second
    yjdot                           Signed35,               -- 2^-30 km/second
    zjdot                           Signed35,               -- 2^-30 km/second
    xjdotdot                        Signed15,               -- 2^-19 km/second/second
    yjdotdot                        Signed15,               -- 2^-19 km/second/second
    zjdotdot                        Signed15,               -- 2^-19 km/second/second

    --Antenna Phase Centre Offset Parameters
    deltaxjpc                       Signed13,               -- 2^-10 metres
    deltayjpc                       Signed13,               -- 2^-10 metres
    deltazjpc                       Signed13,               -- 2^-10 metres

    wordPadding                     Pad3bits
 }


-- ****************************************************************************
-- * GLONASS Scaled Ephemeris and Clock                                       *
-- *                                                                          *
-- * Message name:    DataGLOScaledEphemerisAndClock                          *
-- * Message ID:      6389                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains scaled ephemeris and clock corrections for a       *
-- * single GLONASS satellite.                                                *
-- *                                                                          *
-- * Notes:                                                                   *
-- *                                                                          *
-- * Units and scaling factors for the various parameters can be found in:    *
-- * GLONASS ICD.                                                             *
-- * The message contents depends on the type of navigation message decoded.  *
-- *                                                                          *
-- ****************************************************************************
--
DataGLOScaledEphemerisAndClock ::= SEQUENCE {
    validityTime                    TimeStamp,
    dataSource                      DataSource,
    signal                          GLOMultiSignalID,
    satID                           SatID,
    wordPadding                     Pad13bits,
    gloScaledEphemerisAndClock      GLOSatScaledEphemerisAndClock
}

-- Choices 1 to 8 sent as 0 to 7 down the wire.
-- Padded to use 3 bits.
GLOSatScaledEphemerisAndClock ::= CHOICE {
    fnav                            GLOFNAVSatScaledEphemerisAndClock,
    fmnav                           GLOFMNAVSatScaledEphemerisAndClock,
    cnav                            GLOCNAVSatScaledEphemerisAndClock,
    reserved3                       GLOCNAVSatScaledEphemerisAndClock,   -- used as placeholder
    reserved4                       GLOCNAVSatScaledEphemerisAndClock,   -- used as placeholder
    reserved5                       GLOCNAVSatScaledEphemerisAndClock,   -- used as placeholder
    reserved6                       GLOCNAVSatScaledEphemerisAndClock,   -- used as placeholder
    reserved7                       GLOCNAVSatScaledEphemerisAndClock    -- used as placeholder
}

-- See Table 4.5, ICD L1, L2 GLONASS, Edition 5.1 2008
-- Comment states units and, optionally, (expected range)
GLOFNAVSatScaledEphemerisAndClock ::= SEQUENCE {

   -- Clock Parameters
    wordPadding1                    Pad11bits,
    tkh                             INTEGER (0..23),        -- hours (0-23)
    wordPadding2                    Pad2bits,
    tkm                             INTEGER (0..59),        -- minutes (0-59)
    wordPadding3                    Pad3bits,
    tks                             INTEGER (0..30),        -- seconds (0 or 30)
    wordPadding4                    Pad5bits,
    tb                              INTEGER (0..1425),      -- minutes (15-1425)
    gammantb                        IEEE754Sp,              -- dimensionless
    tauntb                          IEEE754Sp,              -- seconds

    -- Ephemeris Parameters
    xntb                            IEEE754Dp,              -- metres
    yntb                            IEEE754Dp,              -- metres
    zntb                            IEEE754Dp,              -- metres
    xntbdot                         IEEE754Sp,              -- metres/second
    yntbdot                         IEEE754Sp,              -- metres/second
    zntbdot                         IEEE754Sp,              -- metres/second
    xntbdotdot                      IEEE754Sp,              -- metres/second/second
    yntbdotdot                      IEEE754Sp,              -- metres/second/second
    zntbdotdot                      IEEE754Sp,              -- metres/second/second

    -- Flags and Supplementary Parameters
    wordPadding5                    Pad13bits,
    bn                              INTEGER (0..7),         -- dimensionless
    deltataun                       IEEE754Sp,              -- seconds
    wordPadding6                    Pad3bits,
    en                              INTEGER (0..31),        -- days (0-31)
    wordPadding7                    Pad2bits,
    p1                              INTEGER (0..60),        -- minutes
    wordPadding8                    Pad7bits,
    p2                              INTEGER (0..1),         -- dimensionless
    wordPadding9                    Pad7bits,
    p3                              INTEGER (0..1)          -- dimensionless
}

-- See Table 4.5, ICD L1, L2 GLONASS, Edition 5.1 2008
-- Comment states units and, optionally, (expected range)
GLOFMNAVSatScaledEphemerisAndClock ::= SEQUENCE {

   -- Clock Parameters
    wordPadding                     Pad6bits,
    m                               INTEGER (0..3),         -- dimensionless (0-3)
    wordPadding1                    Pad3bits,
    tkh                             INTEGER (0..23),        -- hours (0-23)
    wordPadding2                    Pad2bits,
    tkm                             INTEGER (0..59),        -- minutes (0-59)
    wordPadding3                    Pad3bits,
    tks                             INTEGER (0..30),        -- seconds (0 or 30)
    wordPadding4                    Pad5bits,
    tb                              INTEGER (0..1425),      -- minutes (15-1425)
    gammantb                        IEEE754Sp,              -- dimensionless
    tauntb                          IEEE754Sp,              -- seconds

    -- Ephemeris Parameters
    xntb                            IEEE754Dp,              -- metres
    yntb                            IEEE754Dp,              -- metres
    zntb                            IEEE754Dp,              -- metres
    xntbdot                         IEEE754Sp,              -- metres/second
    yntbdot                         IEEE754Sp,              -- metres/second
    zntbdot                         IEEE754Sp,              -- metres/second
    xntbdotdot                      IEEE754Sp,              -- metres/second/second
    yntbdotdot                      IEEE754Sp,              -- metres/second/second
    zntbdotdot                      IEEE754Sp,              -- metres/second/second

    -- Flags and Supplementary Parameters
    wordPadding5                    Pad5bits,
    bn                              INTEGER (0..7),         -- dimensionless
    wordPadding6                    Pad6bits,
    p                               INTEGER (0..3),         -- dimensionless
    wordPadding7                    Pad5bits,
    nt                              INTEGER (0..1461),      -- days (0-1461)
    wordPadding8                    Pad6bits,
    ft                              INTEGER (0..512),       -- metres
    wordPadding9                    Pad11bits,
    n                               INTEGER (0..31),        -- dimensionless (0-31)
    deltataun                       IEEE754Sp,              -- seconds
    wordPadding10                   Pad3bits,
    en                              INTEGER (0..31),        -- days (0-31)
    wordPadding11                   Pad2bits,
    p1                              INTEGER (0..60),        -- minutes
    wordPadding12                   Pad7bits,
    p2                              INTEGER (0..1),         -- dimensionless
    wordPadding13                   Pad7bits,
    p3                              INTEGER (0..1),         -- dimensionless
    wordPadding14                   Pad7bits,
    p4                              INTEGER (0..1),         -- dimensionless

    -- Satellite Health
    wordPadding15                   Pad7bits,
    ln                              INTEGER (0..1)          -- dimensionless (0 - healthy, 1 - malfunction)
}

-- See string Type 10, 11 & 12, GLONASS ICD, CDMA OS Navigation Signal L1 frequency band, Edition 1.0
-- and GLONASS ICD, CDMA OS Navigation Signal L3 frequency band, Edition 1.0
-- Comment states units and, optionally, (expected range)
GLOCNAVSatScaledEphemerisAndClock ::= SEQUENCE {

    -- Clock Correction Parameters
    wordPadding                     Pad11bits,
    n4                              INTEGER (0..31),        -- 4 year interval
    wordPadding1                    Pad5bits,
    nT                              INTEGER (0..1461),      -- day number
    wordPadding2                    Pad6bits,
    mj                              INTEGER (0..3),         -- dimensionless
    wordPadding3                    Pad2bits,
    ps                              INTEGER (0..63),        -- dimensionless
    wordPadding4                    Pad15bits,
    tb                              INTEGER (0..86310),     -- seconds
    eEj                             IEEE754Sp,              -- seconds
    eTj                             IEEE754Sp,              -- seconds
    wordPadding5                    Pad6bits,
    rEj                             INTEGER (0..3),         -- dimensionless
    wordPadding6                    Pad6bits,
    rTj                             INTEGER (0..3),         -- dimensionless
    fEj                             IEEE754Sp,              -- metres
    fTj                             IEEE754Sp,              -- metres
    tauj                            IEEE754Dp,              -- seconds
    gammaj                          IEEE754Sp,              -- dimensionless
    betaj                           IEEE754Sp,              -- /second
    tauc                            IEEE754Dp,              -- seconds
    taucdot                         IEEE754Sp,              -- seconds/second
    deltataujL2                     IEEE754Sp,              -- seconds
    deltatauGPS                     IEEE754Dp,              -- seconds

    -- Ephemeris Parameters
    xj                              IEEE754Dp,              -- metres
    yj                              IEEE754Dp,              -- metres
    zj                              IEEE754Dp,              -- metres
    xjdot                           IEEE754Dp,              -- metres/second
    yjdot                           IEEE754Dp,              -- metres/second
    zjdot                           IEEE754Dp,              -- metres/second
    xjdotdot                        IEEE754Sp,              -- metres/second/second
    yjdotdot                        IEEE754Sp,              -- metres/second/second
    zjdotdot                        IEEE754Sp,              -- metres/second/second

    --Antenna Phase Centre Offset Parameters
    deltaxjpc                       IEEE754Sp,              -- metres
    deltayjpc                       IEEE754Sp,              -- metres
    deltazjpc                       IEEE754Sp               -- metres
}


-- Ionospheric Correction Messages  --
--
-- These messages provide the unscaled and scaled ionospheric corrections
-- The GNSSs provide different information so implement on a constellation
-- by constellation basis.
--
-- ****************************************************************************
-- * GPS Unscaled Iono Corrections                                            *
-- *                                                                          *
-- * Message name:    DataGPSUnscaledIonoCorrections                          *
-- * Message ID:      6352                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast ionospheric unscaled correction      *
-- * factors received from a single tracked GPS satellite.                    *
-- *                                                                          *
-- * Notes:                                                                   *
-- *                                                                          *
-- * Units, scaling factors, and other semantic information (e.g. reference   *
-- * angles) for the various parameters can be found in:                      *
-- * Interface Specification NAVSTAR GPS.                                     *
-- *                                                                          *
-- ****************************************************************************
--
DataGPSUnscaledIonoCorrections ::= SEQUENCE {
    validityTime                    TimeStamp,
    satID                           SatID,
    dataSource                      DataSource,
    wordPadding                     Pad4bits,
    signal                          GPSSignalID,
    wordPadding1                    Pad13bits,
    gpsSatUnscaledIonoCorrections   GPSSatUnscaledIonoCorrections
}

-- Choices 1 to 8 sent as 0 to 7 down the wire.
-- Padded to use 3 bits.
GPSSatUnscaledIonoCorrections ::= CHOICE {
    lnav                            GPSLNAVSatUnscaledIonoCorrections,
    cnav                            GPSCNAVSatUnscaledIonoCorrections,
    reserved2                       GPSCNAVSatUnscaledIonoCorrections,    -- used as placeholder
    reserved3                       GPSCNAVSatUnscaledIonoCorrections,    -- used as placeholder
    reserved4                       GPSCNAVSatUnscaledIonoCorrections,    -- used as placeholder
    reserved5                       GPSCNAVSatUnscaledIonoCorrections,    -- used as placeholder
    reserved6                       GPSCNAVSatUnscaledIonoCorrections,    -- used as placeholder
    reserved7                       GPSCNAVSatUnscaledIonoCorrections     -- used as placeholder
}

-- Comment states value of least significant bit, if not 1, and units.
GPSLNAVSatUnscaledIonoCorrections ::= SEQUENCE {
    alpha0                          Signed8,                -- 2^-30 seconds
    alpha1                          Signed8,                -- 2^-27 seconds/semi-circle
    alpha2                          Signed8,                -- 2^-24 seconds/semi-circle/semi-circle
    alpha3                          Signed8,                -- 2^-24 seconds/semi-circle/semi-circle/semi-circle
    beta0                           Signed8,                -- 2^11 seconds
    beta1                           Signed8,                -- 2^14 seconds/semi-circle
    beta2                           Signed8,                -- 2^16 seconds/semi-circle/semi-circle
    beta3                           Signed8                 -- 2^16 seconds/semi-circle/semi-circle/semi-circle
}

GPSCNAVSatUnscaledIonoCorrections ::= GPSLNAVSatUnscaledIonoCorrections


-- ****************************************************************************
-- * GPS Scaled Iono Corrections                                              *
-- *                                                                          *
-- * Message name:    DataGPSScaledIonoCorrections                            *
-- * Message ID:      6258                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast ionospheric scaled correction        *
-- * factors received from a single tracked GPS satellite.                    *
-- *                                                                          *
-- * Notes:                                                                   *
-- *                                                                          *
-- * Units, scaling factors, and other semantic information (e.g. reference   *
-- * angles) for the various parameters can be found in:                      *
-- * Interface Specification NAVSTAR GPS.                                     *
-- *                                                                          *
-- ****************************************************************************
--
DataGPSScaledIonoCorrections ::= SEQUENCE {
    validityTime                    TimeStamp,
    satID                           SatID,
    dataSource                      DataSource,
    wordPadding                     Pad4bits,
    signal                          GPSSignalID,
    wordPadding1                    Pad13bits,
    gpsSatScaledIonoCorrections     GPSSatScaledIonoCorrections
}

-- Choices 1 to 8 sent as 0 to 7 down the wire.
-- Padded to use 3 bits.
GPSSatScaledIonoCorrections ::= CHOICE {
    lnav                            GPSLNAVSatScaledIonoCorrections,
    cnav                            GPSCNAVSatScaledIonoCorrections,
    reserved2                       GPSCNAVSatScaledIonoCorrections,    -- used as placeholder
    reserved3                       GPSCNAVSatScaledIonoCorrections,    -- used as placeholder
    reserved4                       GPSCNAVSatScaledIonoCorrections,    -- used as placeholder
    reserved5                       GPSCNAVSatScaledIonoCorrections,    -- used as placeholder
    reserved6                       GPSCNAVSatScaledIonoCorrections,    -- used as placeholder
    reserved7                       GPSCNAVSatScaledIonoCorrections     -- used as placeholder
}

GPSLNAVSatScaledIonoCorrections ::= SEQUENCE {
    alpha0                          IEEE754Sp,              -- seconds
    alpha1                          IEEE754Sp,              -- seconds/radian
    alpha2                          IEEE754Sp,              -- seconds/radian/radian
    alpha3                          IEEE754Sp,              -- seconds/radian/radian/radian
    beta0                           IEEE754Sp,              -- seconds
    beta1                           IEEE754Sp,              -- seconds/radian
    beta2                           IEEE754Sp,              -- seconds/radian/radian
    beta3                           IEEE754Sp               -- seconds/radian/radian/radian
}

GPSCNAVSatScaledIonoCorrections ::= GPSLNAVSatScaledIonoCorrections


-- ****************************************************************************
-- * Galileo Unscaled Iono Corrections                                        *
-- *                                                                          *
-- * Message name:    DataGalUnscaledIonoCorrections                          *
-- * Message ID:      6254                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast unscaled ionospheric correction      *
-- * factors received from a single tracked Galileo satellite.                *
-- *                                                                          *
-- * Notes:                                                                   *
-- *                                                                          *
-- * Units, scaling factors, and other semantic information (e.g. reference   *
-- * angles) for the various parameters can be found in:                      *
-- * Galileo Open Service Signal-in-Space Interface Control Document.         *
-- * sfu is solar flux unit = 10^-22 W/(Hz.m^2)                               *
-- *                                                                          *
-- ****************************************************************************
--
DataGalUnscaledIonoCorrections ::= SEQUENCE {
    validityTime                    TimeStamp,
    satID                           SatID,
    dataSource                      DataSource,
    wordPadding                     Pad4bits,
    signal                          GalSignalID,
    wordPadding1                    Pad13bits,
    galSatUnscaledIonoCorrections   GalSatUnscaledIonoCorrections
}

-- Choices 1 to 8 sent as 0 to 7 down the wire.
-- Padded to use 3 bits.
GalSatUnscaledIonoCorrections ::= CHOICE {
    inav                            GalINAVSatUnscaledIonoCorrections,
    fnav                            GalFNAVSatUnscaledIonoCorrections,
    reserved2                       GalFNAVSatUnscaledIonoCorrections,    -- used as placeholder
    reserved3                       GalFNAVSatUnscaledIonoCorrections,    -- used as placeholder
    reserved4                       GalFNAVSatUnscaledIonoCorrections,    -- used as placeholder
    reserved5                       GalFNAVSatUnscaledIonoCorrections,    -- used as placeholder
    reserved6                       GalFNAVSatUnscaledIonoCorrections,    -- used as placeholder
    reserved7                       GalFNAVSatUnscaledIonoCorrections     -- used as placeholder
}

-- Comment states value of least significant bit, if not 1, and units.
GalINAVSatUnscaledIonoCorrections ::= SEQUENCE {
    ai0                             Unsigned11,             -- 2^-2 sfu
    ai1                             Signed11,               -- 2^-8 sfu/degree
    ai2                             Signed14,               -- 2^-15 sfu/degree/degree
    ionoDisturbanceForRegion1       BOOLEAN,                -- FALSE = None
    ionoDisturbanceForRegion2       BOOLEAN,                -- FALSE = None
    ionoDisturbanceForRegion3       BOOLEAN,                -- FALSE = None
    ionoDisturbanceForRegion4       BOOLEAN,                -- FALSE = None
    ionoDisturbanceForRegion5       BOOLEAN,                -- FALSE = None
    wordPadding1                    Pad7bits
}

GalFNAVSatUnscaledIonoCorrections ::= GalINAVSatUnscaledIonoCorrections


-- ****************************************************************************
-- * Galileo Scaled Iono Corrections                                          *
-- *                                                                          *
-- * Message name:    DataGalScaledIonoCorrections                            *
-- * Message ID:      6261                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast scaled ionospheric correction        *
-- * factors received from a single tracked Galileo satellite.                *
-- *                                                                          *
-- * Notes:                                                                   *
-- *                                                                          *
-- * Units, scaling factors, and other semantic information (e.g. reference   *
-- * angles) for the various parameters can be found in:                      *
-- * Galileo Open Service Signal-in-Space Interface Control Document.         *
-- * sfu is solar flux unit = 10^-22 W/(Hz.m^2)                               *
-- *                                                                          *
-- ****************************************************************************
--
DataGalScaledIonoCorrections ::= SEQUENCE {
    validityTime                    TimeStamp,
    satID                           SatID,
    dataSource                      DataSource,
    wordPadding                     Pad4bits,
    signal                          GalSignalID,
    wordPadding1                    Pad13bits,
    galSatScaledIonoCorrections     GalSatScaledIonoCorrections
}

-- Choices 1 to 8 sent as 0 to 7 down the wire.
-- Padded to use 3 bits.
GalSatScaledIonoCorrections ::= CHOICE {
    fnav                            GalFNAVSatScaledIonoCorrections,
    inav                            GalINAVSatScaledIonoCorrections,
    reserved2                       GalINAVSatScaledIonoCorrections,    -- used as placeholder
    reserved3                       GalINAVSatScaledIonoCorrections,    -- used as placeholder
    reserved4                       GalINAVSatScaledIonoCorrections,    -- used as placeholder
    reserved5                       GalINAVSatScaledIonoCorrections,    -- used as placeholder
    reserved6                       GalINAVSatScaledIonoCorrections,    -- used as placeholder
    reserved7                       GalINAVSatScaledIonoCorrections     -- used as placeholder
}

GalINAVSatScaledIonoCorrections ::= SEQUENCE {
    ai0                             IEEE754Sp,              -- sfu
    ai1                             IEEE754Sp,              -- sfu/degree
    ai2                             IEEE754Sp,              -- sfu/degree/degree
    ionoDisturbanceForRegion1       BOOLEAN,                -- FALSE = None
    ionoDisturbanceForRegion2       BOOLEAN,                -- FALSE = None
    ionoDisturbanceForRegion3       BOOLEAN,                -- FALSE = None
    ionoDisturbanceForRegion4       BOOLEAN,                -- FALSE = None
    ionoDisturbanceForRegion5       BOOLEAN,                -- FALSE = None
    wordPadding1                    Pad11bits
}

GalFNAVSatScaledIonoCorrections ::= GalINAVSatScaledIonoCorrections


-- ****************************************************************************
-- * BeiDou Unscaled Iono Corrections                                         *
-- *                                                                          *
-- * Message name:    DataBDSUnscaledIonoCorrections                          *
-- * Message ID:      6273                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast unscaled ionospheric correction      *
-- * factors received from a single tracked BeiDou satellite.                 *
-- *                                                                          *
-- * Notes:                                                                   *
-- *                                                                          *
-- * Units and scaling factors for the various parameters can be found in:    *
-- * BeiDou Navigation Satellite System Signal In Space ICD.                  *
-- *                                                                          *
-- * TECu is Total Electron Content unit (10^16 electrons/m^2)                *
-- *                                                                          *
-- ****************************************************************************
--
DataBDSUnscaledIonoCorrections ::= SEQUENCE {
    validityTime                    TimeStamp,
    satID                           SatID,
    dataSource                      DataSource,
    wordPadding                     Pad4bits,
    signal                          BDSSignalID,
    wordPadding1                    Pad13bits,
    bdsSatUnscaledIonoCorrections   BDSSatUnscaledIonoCorrections
}

-- Choices 1 to 8 sent as 0 to 7 down the wire.
-- Padded to use 3 bits.
BDSSatUnscaledIonoCorrections ::= CHOICE {
    dnav                            BDSDNAVSatUnscaledIonoCorrections,
    cnav1                           BDSCNAVSatUnscaledIonoCorrections,
    cnav2                           BDSCNAVSatUnscaledIonoCorrections,
    reserved3                       BDSCNAVSatUnscaledIonoCorrections,    -- used as placeholder
    reserved4                       BDSCNAVSatUnscaledIonoCorrections,    -- used as placeholder
    reserved5                       BDSCNAVSatUnscaledIonoCorrections,    -- used as placeholder
    reserved6                       BDSCNAVSatUnscaledIonoCorrections,    -- used as placeholder
    reserved7                       BDSCNAVSatUnscaledIonoCorrections     -- used as placeholder
}

-- See Table 5.5, BeiDou Navigation Satellite System, SIS, ICD, Open Service Signal B1I (Version 3.0), February 2019
-- Comment states value of least significant bit, if not 1, and units
BDSDNAVSatUnscaledIonoCorrections ::= SEQUENCE {
    alpha0                          Signed8,                -- 2^-30 seconds
    alpha1                          Signed8,                -- 2^-27 seconds/semi-circle
    alpha2                          Signed8,                -- 2^-24 seconds/semi-circle/semi-circle
    alpha3                          Signed8,                -- 2^-24 seconds/semi-circle/semi-circle/semi-circle
    beta0                           Signed8,                -- 2^11 seconds
    beta1                           Signed8,                -- 2^14 seconds/semi-circle
    beta2                           Signed8,                -- 2^16 seconds/semi-circle/semi-circle
    beta3                           Signed8                 -- 2^16 seconds/semi-circle/semi-circle/semi-circle
}

-- See Table 7.10,  BeiDou Navigation Satellite System, SIS, ICD, Open Service Signal B2a (Version 1.0), December 2017
-- Comment states value of least significant bit, if not 1, and units
BDSCNAVSatUnscaledIonoCorrections ::= SEQUENCE {
    alpha1                          Unsigned10,             -- 2^-3 TECu
    alpha2                          Signed8,                -- 2^-3 TECu
    alpha3                          Unsigned8,              -- 2^-3 TECu
    alpha4                          Unsigned8,              -- 2^-3 TECu
    alpha5                          Unsigned8,              -- - 2^-3 TECu (note scale factor is negative)
    alpha6                          Signed8,                -- 2^-3 TECu
    alpha7                          Signed8,                -- 2^-3 TECu
    alpha8                          Signed8,                -- 2^-3 TECu
    alpha9                          Signed8,                -- 2^-3 TECu
    wordPadding                     Pad6bits
}

-- ****************************************************************************
-- * BeiDou Scaled Iono Corrections                                           *
-- *                                                                          *
-- * Message name:    DataBDSScaledIonoCorrections                            *
-- * Message ID:      6284                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast scaled ionospheric correction        *
-- * factors received from a single tracked BeiDou satellite.                 *
-- *                                                                          *
-- * Notes:                                                                   *
-- *                                                                          *
-- * Units and scaling factors for the various parameters can be found in:    *
-- * BeiDou Navigation Satellite System Signal In Space ICD.                  *
-- *                                                                          *
-- * TECu is Total Electron Content unit (10^16 electrons/m^2)                *
-- *                                                                          *
-- ****************************************************************************
--
DataBDSScaledIonoCorrections ::= SEQUENCE {
    validityTime                    TimeStamp,
    satID                           SatID,
    dataSource                      DataSource,
    wordPadding                     Pad4bits,
    signal                          BDSSignalID,
    wordPadding1                    Pad13bits,
    bdsSatScaledIonoCorrections     BDSSatScaledIonoCorrections
}

-- Choices 1 to 8 sent as 0 to 7 down the wire.
-- Padded to use 3 bits.
BDSSatScaledIonoCorrections ::= CHOICE {
    dnav                            BDSDNAVSatScaledIonoCorrections,
    cnav1                           BDSCNAVSatScaledIonoCorrections,
    cnav2                           BDSCNAVSatScaledIonoCorrections,
    reserved3                       BDSCNAVSatScaledIonoCorrections,    -- used as placeholder
    reserved4                       BDSCNAVSatScaledIonoCorrections,    -- used as placeholder
    reserved5                       BDSCNAVSatScaledIonoCorrections,    -- used as placeholder
    reserved6                       BDSCNAVSatScaledIonoCorrections,    -- used as placeholder
    reserved7                       BDSCNAVSatScaledIonoCorrections     -- used as placeholder
}

-- See Table 5.5, BeiDou Navigation Satellite System, SIS, ICD, Open Service Signal B1I (Version 3.0), February 2019
-- Comment states units
BDSDNAVSatScaledIonoCorrections ::= SEQUENCE {
    alpha0                          IEEE754Sp,              -- seconds
    alpha1                          IEEE754Sp,              -- seconds/radian
    alpha2                          IEEE754Sp,              -- seconds/radian/radian
    alpha3                          IEEE754Sp,              -- seconds/radian/radian/radian
    beta0                           IEEE754Sp,              -- seconds
    beta1                           IEEE754Sp,              -- seconds/radian
    beta2                           IEEE754Sp,              -- seconds/radian/radian
    beta3                           IEEE754Sp               -- seconds/radian/radian/radian
}

-- See Table 7.10,  BeiDou Navigation Satellite System, SIS, ICD, Open Service Signal B2a (Version 1.0), December 2017
-- Comment states units
BDSCNAVSatScaledIonoCorrections ::= SEQUENCE {
    alpha1                          IEEE754Sp,              -- TECu
    alpha2                          IEEE754Sp,              -- TECu
    alpha3                          IEEE754Sp,              -- TECu
    alpha4                          IEEE754Sp,              -- TECu
    alpha5                          IEEE754Sp,              -- TECu
    alpha6                          IEEE754Sp,              -- TECu
    alpha7                          IEEE754Sp,              -- TECu
    alpha8                          IEEE754Sp,              -- TECu
    alpha9                          IEEE754Sp               -- TECu
}


-- ****************************************************************************
-- * GLONASS Unscaled Iono Corrections                                        *
-- *                                                                          *
-- * Message name:    DataGLOUnscaledIonoCorrections                          *
-- * Message ID:      6458                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast ionospheric unscaled correction      *
-- * factors received from a single tracked GLONASS satellite.                *
-- *                                                                          *
-- * Notes:                                                                   *
-- *                                                                          *
-- * Units and scaling factors for the various parameters can be found in:    *
-- * GLONASS ICD.                                                             *
-- * sfu is solar flux unit = 10^-22 W/(Hz.m^2)                               *
-- *                                                                          *
-- ****************************************************************************
--
DataGLOUnscaledIonoCorrections ::= SEQUENCE {
    validityTime                    TimeStamp,
    satID                           SatID,
    dataSource                      DataSource,
    wordPadding                     Pad4bits,
    signal                          GLOSignalID,
    wordPadding1                    Pad13bits,
    gloSatUnscaledIonoCorrections   GLOSatUnscaledIonoCorrections
}

-- Choices 1 to 8 sent as 0 to 7 down the wire.
-- Padded to use 3 bits.
GLOSatUnscaledIonoCorrections ::= CHOICE {
    fnav                            NULL,                               -- no ionospheric corrections available
    fmnav                           NULL,                               -- no ionospheric corrections available
    cnav                            GLOCNAVSatUnscaledIonoCorrections,
    reserved3                       GLOCNAVSatUnscaledIonoCorrections,  -- used as placeholder
    reserved4                       GLOCNAVSatUnscaledIonoCorrections,  -- used as placeholder
    reserved5                       GLOCNAVSatUnscaledIonoCorrections,  -- used as placeholder
    reserved6                       GLOCNAVSatUnscaledIonoCorrections,  -- used as placeholder
    reserved7                       GLOCNAVSatUnscaledIonoCorrections   -- used as placeholder
}

-- See string Type 25, GLONASS ICD, CDMA OS Navigation Signal L1 frequency band, Edition 1.0
-- and GLONASS ICD, CDMA OS Navigation Signal L3 frequency band, Edition 1.0
-- Comment states value of least significant bit, if not 1, units and, optionally, (expected range)
GLOCNAVSatUnscaledIonoCorrections ::= SEQUENCE {
    cA                              Unsigned9,              -- 2^-7 dimensionless
    cF107                           Unsigned13,             -- 2^-4 sfu
    cAp                             Unsigned9,              -- 2^0 nT
    wordPadding1                    Pad1bits
}


-- ****************************************************************************
-- * GLONASS Scaled Iono Corrections                                          *
-- *                                                                          *
-- * Message name:    DataGLOScaledIonoCorrections                            *
-- * Message ID:      6367                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast ionospheric scaled correction        *
-- * factors received from a single tracked GLONASS satellite.                *
-- *                                                                          *
-- * Notes:                                                                   *
-- *                                                                          *
-- * Units and scaling factors for the various parameters can be found in:    *
-- * GLONASS ICD.                                                             *
-- * sfu is solar flux unit = 10^-22 W/(Hz.m^2)                               *
-- *                                                                          *
-- ****************************************************************************
--
DataGLOScaledIonoCorrections ::= SEQUENCE {
    validityTime                    TimeStamp,
    satID                           SatID,
    dataSource                      DataSource,
    wordPadding                     Pad4bits,
    signal                          GLOSignalID,
    wordPadding1                    Pad13bits,
    gloSatScaledIonoCorrections     GLOSatScaledIonoCorrections
}

-- Choices 1 to 8 sent as 0 to 7 down the wire.
-- Padded to use 3 bits.
GLOSatScaledIonoCorrections ::= CHOICE {
    fnav                            NULL,                               -- no ionospheric corrections available
    fmnav                           NULL,                               -- no ionospheric corrections available
    cnav                            GLOCNAVSatScaledIonoCorrections,
    reserved3                       GLOCNAVSatScaledIonoCorrections,    -- used as placeholder
    reserved4                       GLOCNAVSatScaledIonoCorrections,    -- used as placeholder
    reserved5                       GLOCNAVSatScaledIonoCorrections,    -- used as placeholder
    reserved6                       GLOCNAVSatScaledIonoCorrections,    -- used as placeholder
    reserved7                       GLOCNAVSatScaledIonoCorrections     -- used as placeholder
}

-- See string Type 25, GLONASS ICD, CDMA OS Navigation Signal L1 frequency band, Edition 1.0
-- and GLONASS ICD, CDMA OS Navigation Signal L3 frequency band, Edition 1.0
-- Comment states units and, optionally, (expected range)
GLOCNAVSatScaledIonoCorrections ::= SEQUENCE {
    cA                              IEEE754Sp,              -- dimensionless
    cF107                           IEEE754Sp,              -- sfu
    cAp                             IEEE754Sp               -- nT
}


-- ****************************************************************************
-- * SBAS Message Type 0 - DO NOT USE FOR SAFETY APPLICATIONS MESSAGE         *
-- *                                                                          *
-- * Message name:    DataSBAS0                                               *
-- * Message ID:      6306                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 0 - Do not use ranging data from the sending prn.      *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS0 ::= SEQUENCE {
    validityTime                    TimeStamp,
    satID                           SatID,
    dataSource                      DataSource,
    wordPadding                     Pad4bits,
    signal                          SBASSignalID,
    data                            SEQUENCE (SIZE(14)) OF Unsigned16   -- any data in least significant 212 bits
}


-- ****************************************************************************
-- * SBAS Message Type 1 - PRN Mask                                           *
-- *                                                                          *
-- * Message name:    DataSBAS1                                               *
-- * Message ID:      6377                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 1 - Contains the PRN Mask and IOD PRN.                 *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS1 ::= SEQUENCE {
    validityTime                    TimeStamp,
    satID                           SatID,
    dataSource                      DataSource,
    wordPadding                     Pad4bits,
    signal                          SBASSignalID,
    prnMask                         SEQUENCE (SIZE(14)) OF Unsigned16,  -- PRN mask in least significant 210 bits
    wordPadding1                    Pad14bits,
    iodP                            INTEGER (0..3)                      -- IOD PRN
}


-- ****************************************************************************
-- * SBAS Message Type 2 - Unscaled Fast Corrections Message                  *
-- *                                                                          *
-- * Message name:    DataSBAS2Unscaled                                       *
-- * Message ID:      6371                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 2 - Provides fast unscaled corrections for PRNs as     *
-- * defined in DataSBAS1, slots 0-12.                                        *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS2Unscaled ::= DataSBASUnscaledFastCorrections

DataSBASUnscaledFastCorrections ::= SEQUENCE {
    validityTime                    TimeStamp,
    satID                           SatID,
    dataSource                      DataSource,
    wordPadding                     Pad4bits,
    signal                          SBASSignalID,
    iodF                            Unsigned2,                          -- IOD Fast
    iodP                            Unsigned2,                          -- IOD PRN
    prcF                            SEQUENCE (SIZE(13)) OF Signed12,    -- 0.125 metres
    udrei                           SEQUENCE (SIZE(13)) OF Unsigned4,   -- UDRE Indicators
    wordPadding1                    Pad12bits
}


-- ****************************************************************************
-- * SBAS Message Type 2 - Scaled Fast Corrections Message                    *
-- *                                                                          *
-- * Message name:    DataSBAS2Scaled                                         *
-- * Message ID:      6295                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 2 - Provides fast scaled corrections for PRNs as       *
-- * defined in DataSBAS1, slots 0-12.                                        *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS2Scaled ::= DataSBASScaledFastCorrections

DataSBASScaledFastCorrections ::= SEQUENCE {
    validityTime                    TimeStamp,
    satID                           SatID,
    dataSource                      DataSource,
    wordPadding                     Pad4bits,
    signal                          SBASSignalID,
    wordPadding1                    Pad6bits,
    iodF                            INTEGER (0..3),                     -- IOD Fast
    wordPadding2                    Pad6bits,
    iodP                            INTEGER (0..3),                     -- IOD PRN
    prcF                            SEQUENCE (SIZE(13)) OF IEEE754Sp,   -- metres
    wordPadding3                    Pad8bits,
    udrei                           SEQUENCE (SIZE(13)) OF SEQUENCE {
        wordPadding                     Pad4bits,
        udrei                           INTEGER (0..15)                     -- UDRE Indicators
    }
}


-- ****************************************************************************
-- * SBAS Message Type 3 - Unscaled Fast Corrections Message                  *
-- *                                                                          *
-- * Message name:    DataSBAS3Unscaled                                       *
-- * Message ID:      6289                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 3 - Provides fast unscaled corrections for PRNs as     *
-- * defined in DataSBAS1, slots 13-25.                                       *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS3Unscaled ::= DataSBASUnscaledFastCorrections


-- ****************************************************************************
-- * SBAS Message Type 3 - Scaled Fast Corrections Message                    *
-- *                                                                          *
-- * Message name:    DataSBAS3Scaled                                         *
-- * Message ID:      6394                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 3 - Provides fast scaled corrections for PRNs as       *
-- * defined in DataSBAS1, slots 13-25.                                       *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS3Scaled ::= DataSBASScaledFastCorrections


-- ****************************************************************************
-- * SBAS Message Type 4 - Unscaled Fast Corrections Message                  *
-- *                                                                          *
-- * Message name:    DataSBAS4Unscaled                                       *
-- * Message ID:      6287                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 4 - Provides fast unscaled corrections for PRNs as     *
-- * defined in DataSBAS1, slots 26-38.                                       *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS4Unscaled ::= DataSBASUnscaledFastCorrections


-- ****************************************************************************
-- * SBAS Message Type 4 - Scaled Fast Corrections Message                    *
-- *                                                                          *
-- * Message name:    DataSBAS4Scaled                                         *
-- * Message ID:      6326                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 4 - Provides fast scaled corrections for PRNs as       *
-- * defined in DataSBAS1, slots 26-38.                                       *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS4Scaled ::= DataSBASScaledFastCorrections


-- ****************************************************************************
-- * SBAS Message Type 5 - Unscaled Fast Corrections Message                  *
-- *                                                                          *
-- * Message name:    DataSBAS5Unscaled                                       *
-- * Message ID:      6370                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 5 - Provides fast unscaled corrections for PRNs as     *
-- * defined in DataSBAS1, slots 39-50.                                       *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS5Unscaled ::= DataSBASUnscaledFastCorrections


-- ****************************************************************************
-- * SBAS Message Type 5 - Scaled Fast Corrections Message                    *
-- *                                                                          *
-- * Message name:    DataSBAS5Scaled                                         *
-- * Message ID:      6350                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 5 - Provides fast scaled corrections for PRNs as       *
-- * defined in DataSBAS1, slots 39-50.                                       *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS5Scaled ::= DataSBASScaledFastCorrections


-- ****************************************************************************
-- * SBAS Message Type 6 - Unscaled Integrity Information Message             *
-- *                                                                          *
-- * Message name:    DataSBAS6Unscaled                                       *
-- * Message ID:      6329                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 6 - Provides integrity information for PRNs as defined *
-- * in DataSBAS1.                                                            *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS6Unscaled ::= SEQUENCE {
    validityTime                    TimeStamp,
    satID                           SatID,
    dataSource                      DataSource,
    wordPadding                     Pad4bits,
    signal                          SBASSignalID,
    iodF2                           Unsigned2,                          -- IOD Fast message type 2
    iodF3                           Unsigned2,                          -- IOD Fast message type 3
    iodF4                           Unsigned2,                          -- IOD Fast message type 4
    iodF5                           Unsigned2,                          -- IOD Fast message type 5
    udrei                           SEQUENCE (SIZE(51)) OF Unsigned4,   -- UDRE Indicators
    wordPadding1                    Pad12bits
}


-- ****************************************************************************
-- * SBAS Message Type 6 - Scaled Integrity Information Message               *
-- *                                                                          *
-- * Message name:    DataSBAS6Scaled                                         *
-- * Message ID:      6323                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 6 - Provides integrity information for PRNs as defined *
-- * in DataSBAS1.                                                            *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS6Scaled ::= SEQUENCE {
    validityTime                    TimeStamp,
    satID                           SatID,
    dataSource                      DataSource,
    wordPadding                     Pad4bits,
    signal                          SBASSignalID,
    wordPadding1                    Pad6bits,
    iodF2                           Unsigned2,                          -- IOD Fast message type 2
    wordPadding2                    Pad6bits,
    iodF3                           Unsigned2,                          -- IOD Fast message type 3
    wordPadding3                    Pad6bits,
    iodF4                           Unsigned2,                          -- IOD Fast message type 4
    wordPadding4                    Pad6bits,
    iodF5                           Unsigned2,                          -- IOD Fast message type 5
    wordPadding5                    Pad8bits,
    udrei                           SEQUENCE (SIZE(51)) OF SEQUENCE {
        wordPadding                     Pad4bits,
        udrei                           INTEGER (0..15)                     -- UDRE Indicators
    }
}


-- ****************************************************************************
-- * SBAS Message Type 7 - Unscaled Fast Correction Degradation Factor        *
-- *                                                                          *
-- * Message name:    DataSBAS7Unscaled                                       *
-- * Message ID:      6406                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 7 - Provides fast correction degradation factors for   *
-- * PRNs as defined in DataSBAS1.                                            *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS7Unscaled ::= SEQUENCE {
    validityTime                    TimeStamp,
    satID                           SatID,
    dataSource                      DataSource,
    wordPadding                     Pad4bits,
    signal                          SBASSignalID,
    tLatency                        Unsigned4,                          -- System latency seconds
    iodP                            Unsigned2,                          -- IOD PRN
    spare                           Unsigned2,                          -- spare
    dfi                             SEQUENCE (SIZE(51)) OF Unsigned4,   -- degradation factor indicators
    wordPadding1                    Pad12bits
}


-- ****************************************************************************
-- * SBAS Message Type 7 - Scaled Fast Correction Degradation Factor          *
-- *                                                                          *
-- * Message name:    DataSBAS7Scaled                                         *
-- * Message ID:      6396                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 7 - Provides fast correction degradation factors for   *
-- * PRNs as defined in DataSBAS1.                                            *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS7Scaled ::= SEQUENCE {
    validityTime                    TimeStamp,
    satID                           SatID,
    dataSource                      DataSource,
    wordPadding                     Pad4bits,
    signal                          SBASSignalID,
    wordPadding1                    Pad4bits,
    tLatency                        INTEGER (0..15),                    -- System latency seconds
    wordPadding2                    Pad6bits,
    iodP                            INTEGER (0..3),                     -- IOD PRN
    wordPadding3                    Pad14bits,
    spare                           Unsigned2,                          -- spare
    wordPadding4                    Pad8bits,
    dfi                             SEQUENCE (SIZE(51)) OF SEQUENCE {
        wordPadding                     Pad4bits,
        dfi                             INTEGER (0..15)                     -- degradation factor indicators
    }
}


-- ****************************************************************************
-- * SBAS Message Type 9 - Unscaled GEO Navigation Message                    *
-- *                                                                          *
-- * Message name:    DataSBAS9Unscaled                                       *
-- * Message ID:      6455                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 9 - This message contains unscaled GEO navigation      *
-- * message parameters for a single SBAS satellite.                          *
-- *                                                                          *
-- * Notes:                                                                   *
-- *                                                                          *
-- * Units, scaling factors, and other semantic information for the various   *
-- * parameters can be found in: Minimum Operational Performance Standards    *
-- * For Global Positioning System/Wide Area Augmentation System Airborne     *
-- * Equipment.                                                               *
-- * Comment states value of least significant bit, if not 1, and units.      *
-- *                                                                          *
-- ****************************************************************************
--
DataSBAS9Unscaled ::= SEQUENCE {
    validityTime                    TimeStamp,
    dataSource                      DataSource,
    signal                          SBASMultiSignalID,
    satID                           SatID,
    res                             Unsigned8,              -- reserved
    t0                              Unsigned13,             -- 16 seconds
    ura                             Unsigned4,              -- URA of 15 shows satellite ranging signal should not be used
    xG                              Signed30,               -- 0.08 metres
    yG                              Signed30,               -- 0.08 metres
    zG                              Signed25,               -- 0.4 metres
    xGdot                           Signed17,               -- 0.000625 metres/second
    yGdot                           Signed17,               -- 0.000625 metres/second
    zGdot                           Signed18,               -- 0.004 metres/second
    xGdot2                          Signed10,               -- 0.0000125 metres/second/second
    yGdot2                          Signed10,               -- 0.0000125 metres/second/second
    zGdot2                          Signed10,               -- 0.0000625 metres/second/second
    aGf0                            Signed12,               -- 2^-31 seconds
    aGf1                            Signed8,                -- 2^-40 seconds/second
    wordPadding                     Pad12bits
}


-- ****************************************************************************
-- * SBAS Message Type 9 - Scaled GEO Navigation Message                      *
-- *                                                                          *
-- * Message name:    DataSBAS9Scaled                                         *
-- * Message ID:      6440                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 9 - This message contains scaled GEO navigation        *
-- * message parameters for a single SBAS satellite.                          *
-- *                                                                          *
-- * Notes:                                                                   *
-- *                                                                          *
-- * Units, scaling factors, and other semantic information for the various   *
-- * parameters can be found in: Minimum Operational Performance Standards    *
-- * For Global Positioning System/Wide Area Augmentation System Airborne     *
-- * Equipment.                                                               *
-- *                                                                          *
-- ****************************************************************************
--
DataSBAS9Scaled ::= SEQUENCE {
    validityTime                    TimeStamp,
    dataSource                      DataSource,
    signal                          SBASMultiSignalID,
    satID                           SatID,
    wordPadding                     Pad8bits,
    res                             INTEGER (0..255),       -- reserved
    wordPadding1                    Pad15bits,
    t0                              INTEGER (0..86384),     -- seconds
    wordPadding2                    Pad12bits,
    ura                             INTEGER (0..15),        -- URA of 15 shows satellite ranging signal should not be used
    xG                              IEEE754Dp,              -- metres
    yG                              IEEE754Dp,              -- metres
    zG                              IEEE754Dp,              -- metres
    xGdot                           IEEE754Sp,              -- metres/second
    yGdot                           IEEE754Sp,              -- metres/second
    zGdot                           IEEE754Sp,              -- metres/second
    xGdot2                          IEEE754Sp,              -- metres/second/second
    yGdot2                          IEEE754Sp,              -- metres/second/second
    zGdot2                          IEEE754Sp,              -- metres/second/second
    aGf0                            IEEE754Sp,              -- seconds
    aGf1                            IEEE754Sp               -- seconds/second
}


-- ****************************************************************************
-- * SBAS Message Type 10 - Unscaled Degradation Factors Message              *
-- *                                                                          *
-- * Message name:    DataSBAS10Unscaled                                      *
-- * Message ID:      6288                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 10 - Provides degradation factors.                     *
-- *                                                                          *
-- * Notes:                                                                   *
-- *                                                                          *
-- * Details can be found in: Minimum Operational Performance Standards       *
-- * For Global Positioning System/Wide Area Augmentation System Airborne     *
-- * Equipment.                                                               *
-- * Comment states value of least significant bit, if not 1, and units.      *
-- *                                                                          *
-- ****************************************************************************
--
DataSBAS10Unscaled ::= SEQUENCE {
    validityTime                    TimeStamp,
    satID                           SatID,
    dataSource                      DataSource,
    wordPadding                     Pad4bits,
    signal                          SBASSignalID,
    pBrrc                           Unsigned10,                 -- 0.002 metres
    pCltclsb                        Unsigned10,                 -- 0.002 metres
    pCltcv1                         Unsigned10,                 -- 0.00005 metres/second
    pIltcv1                         Unsigned9,                  -- seconds
    pCltcv0                         Unsigned10,                 -- 0.002 metres
    pIltcv0                         Unsigned9,                  -- seconds
    pCgeolsb                        Unsigned10,                 -- 0.0005 metres
    pCgeov                          Unsigned10,                 -- 0.00005 metres/second
    pIgeo                           Unsigned9,                  -- seconds
    pCer                            Unsigned6,                  -- 0.5 metres
    pCionostep                      Unsigned10,                 -- 0.001 metres
    pIiono                          Unsigned9,                  -- seconds
    pCionoramp                      Unsigned10,                 -- 0.000005 metres/second
    pRSSUDRE                        Unsigned1,                  -- unitless
    pRSSiono                        Unsigned1,                  -- unitless
    pCcovariance                    Unsigned7,                  -- 0.1 unitless
    spare1                          Unsigned1,                  -- spare bit
    spare80                         OCTET STRING (SIZE(10)),    -- spare 80 bits
    wordPadding1                    Pad12bits
}


-- ****************************************************************************
-- * SBAS Message Type 10 - Scaled Degradation Factors Message                *
-- *                                                                          *
-- * Message name:    DataSBAS10Scaled                                        *
-- * Message ID:      6297                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 10 - Provides degradation factors.                     *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS10Scaled ::= SEQUENCE {
    validityTime                    TimeStamp,
    satID                           SatID,
    dataSource                      DataSource,
    wordPadding                     Pad4bits,
    signal                          SBASSignalID,
    pBrrc                           IEEE754Sp,                  -- metres
    pCltclsb                        IEEE754Sp,                  -- metres
    pCltcv1                         IEEE754Sp,                  -- metres/second
    pIltcv1                         IEEE754Sp,                  -- seconds
    pCltcv0                         IEEE754Sp,                  -- metres
    pIltcv0                         IEEE754Sp,                  -- seconds
    pCgeolsb                        IEEE754Sp,                  -- metres
    pCgeov                          IEEE754Sp,                  -- metres/second
    pIgeo                           IEEE754Sp,                  -- seconds
    pCer                            IEEE754Sp,                  -- metres
    pCionostep                      IEEE754Sp,                  -- metres
    pIiono                          IEEE754Sp,                  -- seconds
    pCionoramp                      IEEE754Sp,                  -- metres/second
    pCcovariance                    IEEE754Sp,                  -- unitless
    pRSSUDRE                        BOOLEAN,                    -- unitless
    pRSSiono                        BOOLEAN,                    -- unitless
    wordPadding1                    Pad14bits,
    spare80                         OCTET STRING (SIZE(10)),    -- spare 80 bits
    spare1                          Unsigned1,                  -- spare bit
    wordPadding2                    Pad15bits
}


-- ****************************************************************************
-- * SBAS Message Type 12 - Unscaled SBAS Network Time/UTC/GLONASS Offset     *
-- *                                                                          *
-- * Message name:    DataSBAS12Unscaled                                      *
-- * Message ID:      6385                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 12 - SBAS Network time offset to UTC/GLONASS.          *
-- *                                                                          *
-- * Notes:                                                                   *
-- *                                                                          *
-- * Details can be found in: Minimum Operational Performance Standards       *
-- * For Global Positioning System/Wide Area Augmentation System Airborne     *
-- * Equipment.                                                               *
-- * Comment states value of least significant bit, if not 1, and units.      *
-- *                                                                          *
-- ****************************************************************************
--
DataSBAS12Unscaled ::= SEQUENCE {
    validityTime                    TimeStamp,
    satID                           SatID,
    dataSource                      DataSource,
    wordPadding                     Pad4bits,
    signal                          SBASSignalID,
    pA1SNT                          Signed24,                   -- 2^-50 seconds/second - first order term of polynomial
    pA0SNT                          Signed32,                   -- 2^-30 seconds - constant term of polynomial
    ptot                            Unsigned8,                  -- 2^12 seconds - UTC reference time
    pWNt                            Unsigned8,                  -- weeks - UTC reference week number
    pDeltatLS                       Signed8,                    -- seconds - delta time due to leap seconds
    pWNLSF                          Unsigned8,                  -- weeks - week number the leap second becomes effective
    pDN                             Unsigned8,                  -- days - day the leap second becomes effective
    pDeltatLSF                      Signed8,                    -- seconds - delta time due to leap seconds
    pUTCID                          Unsigned3,                  -- UTC Standard Identifier
    pGPSToW                         Unsigned20,                 -- seconds - GPS Time of Week
    pGPSWN                          Unsigned10,                 -- weeks - GPS Week Number
    pGLONASSIndicator               Unsigned1,                  -- unitless
    pGLONASSTimeOffset              SEQUENCE (SIZE(5)) OF Unsigned16,   -- reserved in least significant 74 bits
    wordPadding1                    Pad6bits
}


-- ****************************************************************************
-- * SBAS Message Type 12 - Scaled SBAS Network Time/UTC/GLONASS Offset       *
-- *                                                                          *
-- * Message name:    DataSBAS12Scaled                                        *
-- * Message ID:      6286                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 12 - SBAS Network time offset to UTC/GLONASS.          *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS12Scaled ::= SEQUENCE {
    validityTime                    TimeStamp,
    satID                           SatID,
    dataSource                      DataSource,
    wordPadding                     Pad4bits,
    signal                          SBASSignalID,
    pA1SNT                          IEEE754Sp,                  -- seconds/second - first order term of polynomial
    pA0SNT                          IEEE754Dp,                  -- seconds - constant term of polynomial
    wordPadding1                    Pad12bits,
    ptot                            INTEGER (0..602112),        -- seconds - UTC reference time
    pWNt                            INTEGER (0..255),           -- weeks - UTC reference week number
    pDeltatLS                       INTEGER (-128..127),        -- seconds - delta time due to leap seconds
    pWNLSF                          INTEGER (0..255),           -- weeks - week number the leap second becomes effective
    wordPadding2                    Pad5bits,
    pDN                             INTEGER (1..7),             -- days - day the leap second becomes effective
    pDeltatLSF                      INTEGER (-128..127),        -- seconds - delta time due to leap seconds
    wordPadding3                    Pad5bits,
    pUTCID                          INTEGER (0..7),             -- UTC Standard Identifier
    wordPadding4                    Pad12bits,
    pGPSToW                         INTEGER (0..604799),        -- seconds - GPS Time of Week
    wordPadding5                    Pad6bits,
    pGPSWN                          INTEGER (0..1023),          -- weeks - GPS Week Number
    wordPadding6                    Pad15bits,
    pGLONASSIndicator               INTEGER (0..1),             -- unitless
    pGLONASSTimeOffset              SEQUENCE (SIZE(5)) OF Unsigned16    -- reserved in least significant 74 bits
}


-- ****************************************************************************
-- * SBAS Message Type 17 - Unscaled Almanac                                  *
-- *                                                                          *
-- * Message name:    DataSBAS17Unscaled                                      *
-- * Message ID:      6310                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 17 - This message contains the unscaled almanac        *
-- * parameters received from the tracked SBAS satellites.                    *
-- *                                                                          *
-- * Notes:                                                                   *
-- *                                                                          *
-- * The signal ID refers to where the message has come from.                 *
-- * Units, scaling factors, and other semantic information for the various   *
-- * parameters can be found in: Minimum Operational Performance Standards    *
-- * For Global Positioning System/Wide Area Augmentation System Airborne     *
-- * Equipment.                                                               *
-- * Comment states value of least significant bit, if not 1, and units.      *
-- *                                                                          *
-- ****************************************************************************
--
DataSBAS17Unscaled ::= SEQUENCE {
    validityTime                    TimeStamp,
    numberOfMessages                Unsigned8,              -- Number of messages to report almanac
    messageNumber                   Unsigned8,              -- Number of message being reported (0 to N-1)
    dataSource                      DataSource,
    signalID                        SBASMultiSignalID,
    wordPadding                     Pad10bits,
    sbasSatUnscaledAlmanacs SEQUENCE (SIZE(0..63)) OF SEQUENCE {
        timeOfDay                       Unsigned11,             -- 64 seconds
        dataID                          Unsigned2,              -- unitless
        prnNumber                       Unsigned8,              -- unitless
        healthAndStatus                 Unsigned8,              -- unitless
        xG                              Signed15,               -- 2,600 metres
        yG                              Signed15,               -- 2,600 metres
        zG                              Signed9,                -- 26,000 metres
        xGdot                           Signed3,                -- 10 metres/second
        yGdot                           Signed3,                -- 10 metres/second
        zGdot                           Signed4,                -- 60 metres/second
        wordPadding                     Pad2bits
    }
}


-- ****************************************************************************
-- * SBAS Message Type 17 - Scaled Almanac                                    *
-- *                                                                          *
-- * Message name:    DataSBAS17Scaled                                        *
-- * Message ID:      6337                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 17 - This message contains the scaled almanac          *
-- * parameters received from the tracked SBAS satellites.                    *
-- *                                                                          *
-- * Notes:                                                                   *
-- *                                                                          *
-- * The signal ID refers to where the message has come from.                 *
-- * Units, scaling factors, and other semantic information for the various   *
-- * parameters can be found in: Minimum Operational Performance Standards    *
-- * For Global Positioning System/Wide Area Augmentation System Airborne     *
-- * Equipment.                                                               *
-- *                                                                          *
-- ****************************************************************************
--
DataSBAS17Scaled ::= SEQUENCE {
    validityTime                    TimeStamp,
    numberOfMessages                Unsigned8,              -- Number of messages to report almanac
    messageNumber                   Unsigned8,              -- Number of message being reported (0 to N-1)
    dataSource                      DataSource,
    signalID                        SBASMultiSignalID,
    wordPadding                     Pad10bits,
    sbasSatScaledAlmanacs SEQUENCE (SIZE(0..63)) OF SEQUENCE {
        timeOfDay                       IEEE754Sp,              -- seconds
        wordPadding                     Pad8bits,
        dataID                          Unsigned8,              -- unitless
        wordPadding1                    Pad8bits,
        prnNumber                       Unsigned8,              -- unitless
        wordPadding2                    Pad8bits,
        healthAndStatus                 Unsigned8,              -- unitless
        xG                              IEEE754Sp,              -- metres
        yG                              IEEE754Sp,              -- metres
        zG                              IEEE754Sp,              -- metres
        xGdot                           IEEE754Sp,              -- metres/second
        yGdot                           IEEE754Sp,              -- metres/second
        zGdot                           IEEE754Sp               -- metres/second
    }
}


-- ****************************************************************************
-- * SBAS Message Type 18 - Unscaled Iono Corrections - IGP Mask              *
-- *                                                                          *
-- * Message name:    DataSBAS18Unscaled                                      *
-- * Message ID:      6387                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 18 - This message contains the broadcast unscaled      *
-- * ionospheric correction factors received from a single tracked SBAS       *
-- * satellite.                                                               *
-- *                                                                          *
-- * Notes:                                                                   *
-- *                                                                          *
-- * Units, scaling factors, and other semantic information for the various   *
-- * parameters can be found in: Minimum Operational Performance Standards    *
-- * For Global Positioning System/Wide Area Augmentation System Airborne     *
-- * Equipment.                                                               *
-- *                                                                          *
-- ****************************************************************************
--
DataSBAS18Unscaled ::= SEQUENCE {
    validityTime                    TimeStamp,
    satID                           SatID,
    dataSource                      DataSource,
    wordPadding                     Pad4bits,
    signal                          SBASSignalID,
    nBands                          Unsigned4,              -- unitless (0-11)
    bandNumber                      Unsigned4,              -- unitless (0-10)
    iodi                            Unsigned2,              -- unitless (0-3)
    igpMask                         BIT STRING (SIZE(201)), -- unitless
    spare                           BIT STRING (SIZE(1)),
    wordPadding1                    Pad12bits
}


-- ****************************************************************************
-- * SBAS Message Type 18 - Scaled Iono Corrections - IGP Mask                *
-- *                                                                          *
-- * Message name:    DataSBAS18Scaled                                        *
-- * Message ID:      6357                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 18 - This message contains the broadcast scaled        *
-- * ionospheric correction factors received from a single tracked SBAS       *
-- * satellite.                                                               *
-- *                                                                          *
-- * Notes:                                                                   *
-- *                                                                          *
-- * Units, scaling factors, and other semantic information for the various   *
-- * parameters can be found in: Minimum Operational Performance Standards    *
-- * For Global Positioning System/Wide Area Augmentation System Airborne     *
-- * Equipment.                                                               *
-- *                                                                          *
-- ****************************************************************************
--
DataSBAS18Scaled ::= SEQUENCE {
    validityTime                    TimeStamp,
    satID                           SatID,
    dataSource                      DataSource,
    wordPadding                     Pad4bits,
    signal                          SBASSignalID,
    nBands                          Unsigned8,              -- unitless (0-11)
    bandNumber                      Unsigned8,              -- unitless (0-10)
    wordPadding1                    Pad8bits,
    iodi                            Unsigned8,              -- unitless (0-3)
    igpMask                         SEQUENCE (SIZE(13)) OF Unsigned16 -- unitless - mask is in the 201 least significant bits
}


-- ****************************************************************************
-- * SBAS Message Type 24 - Unscaled Mixed Fast/Long Term Error Corrections   *
-- *                                                                          *
-- * Message name:    DataSBAS24Unscaled                                      *
-- * Message ID:      6399                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 24 - Provides Mixed Fast Corrections and Long Term     *
-- * Satellite Error Corrections.                                             *
-- *                                                                          *
-- * Notes:                                                                   *
-- *                                                                          *
-- * Details can be found in: Minimum Operational Performance Standards       *
-- * For Global Positioning System/Wide Area Augmentation System Airborne     *
-- * Equipment.                                                               *
-- * Comment states value of least significant bit, if not 1, and units.      *
-- *                                                                          *
-- ****************************************************************************
--
DataSBAS24Unscaled ::= SEQUENCE {
    validityTime                    TimeStamp,
    satID                           SatID,
    dataSource                      DataSource,
    wordPadding                     Pad4bits,
    signal                          SBASSignalID,
    prcF                            SEQUENCE (SIZE(6)) OF Signed12,     -- 0.125 metres
    udrei                           SEQUENCE (SIZE(6)) OF Unsigned4,    -- UDRE Indicators
    iodP                            Unsigned2,                  -- IOD PRN
    blockID                         Unsigned2,                  -- Block ID 0-3 maps to Message type ID 2-5
    iodF                            Unsigned2,                  -- IOD Fast
    spare                           Unsigned4,
    longTermCorrection              SBASUnscaledLongTermCorrection,
    wordPadding1                    Pad12bits
}


-- ****************************************************************************
-- * SBAS Message Type 24 - Scaled Mixed Fast/Long Term Error Corrections     *
-- *                                                                          *
-- * Message name:    DataSBAS24Scaled                                        *
-- * Message ID:      6303                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 24 - Provides Mixed Fast Corrections and Long Term     *
-- * Satellite Error Corrections.                                             *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS24Scaled ::= SEQUENCE {
    validityTime                    TimeStamp,
    satID                           SatID,
    dataSource                      DataSource,
    wordPadding                     Pad4bits,
    signal                          SBASSignalID,
    wordPadding1                    Pad6bits,
    iodP                            INTEGER (0..3),             -- IOD PRN
    wordPadding2                    Pad6bits,
    blockID                         INTEGER (0..3),             -- Block ID 0-3 maps to Message type ID 2-5
    wordPadding3                    Pad6bits,
    iodF                            INTEGER (0..3),             -- IOD Fast
    wordPadding4                    Pad8bits,
    prcF                            SEQUENCE (SIZE(6)) OF IEEE754Sp,    -- metres
    udrei                           SEQUENCE (SIZE(6)) OF SEQUENCE {
        wordPadding                     Pad4bits,
        udrei                           INTEGER (0..15)             -- UDRE Indicators
    },
    wordPadding5                    Pad15bits,
    longTermCorrection              SBASScaledLongTermCorrection
}


-- ****************************************************************************
-- * SBAS Message Type 25 - Unscaled Long Term Satellite Error Corrections    *
-- *                                                                          *
-- * Message name:    DataSBAS25Unscaled                                      *
-- * Message ID:      6360                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 25 - Provides Long Term Satellite Error Corrections.   *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS25Unscaled ::= SEQUENCE {
    validityTime                    TimeStamp,
    satID                           SatID,
    dataSource                      DataSource,
    wordPadding                     Pad4bits,
    signal                          SBASSignalID,
    longTermCorrections             SEQUENCE (SIZE(2)) OF SBASUnscaledLongTermCorrection,
    wordPadding1                    Pad12bits
}

-- Comment states value of least significant bit, if not 1, and units.
SBASUnscaledLongTermCorrection ::= CHOICE {
    velCode0Message                 SEQUENCE {
        deltas                          SEQUENCE (SIZE(2)) OF SEQUENCE {
            prnMask                         Unsigned6,                  -- PRN Mask Number
            iod                             Unsigned8,                  -- Issue of Data
            deltax                          Signed9,                    -- 0.125 metres
            deltay                          Signed9,                    -- 0.125 metres
            deltaz                          Signed9,                    -- 0.125 metres
            deltaaf0                        Signed10                    -- 2^-31 seconds
            },
        iodP                            Unsigned2,                  -- Issue of Data PRN
        spare                           Unsigned1
    },
    velCode1Message                 SEQUENCE {
        prnMask                         Unsigned6,                  -- PRN Mask Number
        iod                             Unsigned8,                  -- Issue of Data
        deltax                          Signed11,                   -- 0.125 metres
        deltay                          Signed11,                   -- 0.125 metres
        deltaz                          Signed11,                   -- 0.125 metres
        deltaaf0                        Signed11,                   -- 2^-31 seconds
        deltaxdot                       Signed8,                    -- 2^-11 metres/second
        deltaydot                       Signed8,                    -- 2^-11 metres/second
        deltazdot                       Signed8,                    -- 2^-11 metres/second
        deltaaf1                        Signed8,                    -- 2^-39 seconds/second
        toda                            Signed13,                   -- 16 seconds
        iodP                            Unsigned2                   -- Issue of Data PRN
    }
}


-- ****************************************************************************
-- * SBAS Message Type 25 - Scaled Long Term Satellite Error Corrections      *
-- *                                                                          *
-- * Message name:    DataSBAS25Scaled                                        *
-- * Message ID:      6441                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 25 - Provides Long Term Satellite Error Corrections.   *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS25Scaled ::= SEQUENCE {
    validityTime                    TimeStamp,
    satID                           SatID,
    dataSource                      DataSource,
    wordPadding                     Pad4bits,
    signal                          SBASSignalID,
    longTermCorrections             SEQUENCE (SIZE(2)) OF SEQUENCE {
        wordPadding                     Pad15bits,
        longTermCorrection              SBASScaledLongTermCorrection
    }
}

SBASScaledLongTermCorrection ::= CHOICE {
    velCode0Message                 SEQUENCE {
        deltas                          SEQUENCE (SIZE(2)) OF SEQUENCE {
            wordPadding                     Pad2bits,
            prnMask                         Unsigned6,                  -- PRN Mask Number
            iod                             Unsigned8,                  -- Issue of Data
            deltax                          IEEE754Sp,                  -- metres
            deltay                          IEEE754Sp,                  -- metres
            deltaz                          IEEE754Sp,                  -- metres
            deltaaf0                        IEEE754Sp                   -- seconds
            },
        wordPadding                     Pad6bits,
        iodP                            Unsigned2,                  -- Issue of Data PRN
        wordPadding1                    Pad7bits,
        spare                           Unsigned1
    },
    velCode1Message                 SEQUENCE {
        wordPadding                     Pad2bits,
        prnMask                         Unsigned6,                  -- PRN Mask Number
        iod                             Unsigned8,                  -- Issue of Data
        deltax                          IEEE754Sp,                  -- metres
        deltay                          IEEE754Sp,                  -- metres
        deltaz                          IEEE754Sp,                  -- metres
        deltaaf0                        IEEE754Sp,                  -- seconds
        deltaxdot                       IEEE754Sp,                  -- metres/second
        deltaydot                       IEEE754Sp,                  -- metres/second
        deltazdot                       IEEE754Sp,                  -- metres/second
        deltaaf1                        IEEE754Sp,                  -- seconds/second
        toda                            IEEE754Sp,                  -- seconds
        wordPadding1                    Pad14bits,
        iodP                            Unsigned2                   -- Issue of Data PRN
    }
}


-- ****************************************************************************
-- * SBAS Message Type 26 - Unscaled Ionospheric Delay Corrections            *
-- *                                                                          *
-- * Message name:    DataSBAS26Unscaled                                      *
-- * Message ID:      6409                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 26 - This message contains the broadcast unscaled      *
-- * ionospheric correction factors received from a single tracked SBAS       *
-- * satellite.                                                               *
-- *                                                                          *
-- * Notes:                                                                   *
-- *                                                                          *
-- * Units, scaling factors, and other semantic information for the various   *
-- * parameters can be found in: Minimum Operational Performance Standards    *
-- * For Global Positioning System/Wide Area Augmentation System Airborne     *
-- * Equipment.                                                               *
-- * Comment states value of least significant bit, if not 1, and units.      *
-- *                                                                          *
-- ****************************************************************************
--
DataSBAS26Unscaled ::= SEQUENCE {
    validityTime                    TimeStamp,
    satID                           SatID,
    dataSource                      DataSource,
    wordPadding                     Pad4bits,
    signal                          SBASSignalID,
    bandNumber                      Unsigned4,              -- unitless (0-10)
    blockID                         Unsigned4,              -- unitless (0-13)
    igpBlock                        SEQUENCE (SIZE(15)) OF SEQUENCE {
        igpVDE                          Unsigned9,              -- 0.125 metres
        igpGIVEI                        Unsigned4               -- unitless
    },
    iodi                            Unsigned2,              -- unitless (0-3)
    spare                           BIT STRING (SIZE(7)),
    wordPadding1                    Pad12bits
}


-- ****************************************************************************
-- * SBAS Message Type 26 - Scaled Ionospheric Delay Corrections              *
-- *                                                                          *
-- * Message name:    DataSBAS26Scaled                                        *
-- * Message ID:      6379                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 26 - This message contains the broadcast scaled        *
-- * ionospheric correction factors received from a single tracked SBAS       *
-- * satellite.                                                               *
-- *                                                                          *
-- * Notes:                                                                   *
-- *                                                                          *
-- * Units, scaling factors, and other semantic information for the various   *
-- * parameters can be found in: Minimum Operational Performance Standards    *
-- * For Global Positioning System/Wide Area Augmentation System Airborne     *
-- * Equipment.                                                               *
-- *                                                                          *
-- ****************************************************************************
--
DataSBAS26Scaled ::= SEQUENCE {
    validityTime                    TimeStamp,
    satID                           SatID,
    dataSource                      DataSource,
    wordPadding                     Pad4bits,
    signal                          SBASSignalID,
    bandNumber                      Unsigned8,              -- unitless (0-10)
    blockID                         Unsigned8,              -- unitless (0-13)
    igpBlock                        SEQUENCE (SIZE(15)) OF SEQUENCE {
        igpVDE                          IEEE754Sp,              -- metres
        igpGIVEI                        Unsigned16              -- unitless
    },
    iodi                            Unsigned8,              -- unitless (0-3)
    wordPadding1                    Pad1bits,
    spare                           Unsigned7
}


-- ****************************************************************************
-- * SBAS Message Type 27 - Service Message                                   *
-- *                                                                          *
-- * Message name:    DataSBAS27Unscaled                                      *
-- * Message ID:      6431                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 27 - Provides SBAS Service Messages.                   *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS27Unscaled ::= SEQUENCE {
    validityTime                    TimeStamp,
    satID                           SatID,
    dataSource                      DataSource,
    wordPadding                     Pad4bits,
    signal                          SBASSignalID,
    iods                            Unsigned3,              -- Issue of Data Service
    msgCount                        Unsigned3,              -- Number of service messages
    msgNumber                       Unsigned3,              -- Service message number
    regionCount                     Unsigned3,              -- Number of regions
    priorityCode                    Unsigned2,
    deltaUDREInside                 Unsigned4,              -- Delta UDRE Inside
    deltaUDREOutside                Unsigned4,              -- Delta UDRE Outside
    regions                         SEQUENCE (SIZE(5)) OF SEQUENCE {
        c1Lat                           Signed8,                -- Coordinate 1 latitude degrees
        c1Lon                           Signed9,                -- Coordinate 1 longitude degrees
        c2Lat                           Signed8,                -- Coordinate 2 latitude degrees
        c2Lon                           Signed9,                -- Coordinate 2 longitude degrees
        shape                           Unsigned1
    },
    spare                           Unsigned15,
    wordPadding1                    Pad12bits
}


-- ****************************************************************************
-- * SBAS Message Type 27 - Service Message                                   *
-- *                                                                          *
-- * Message name:    DataSBAS27Scaled                                        *
-- * Message ID:      6347                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 27 - Provides SBAS Service Messages.                   *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS27Scaled ::= SEQUENCE {
    validityTime                    TimeStamp,
    satID                           SatID,
    dataSource                      DataSource,
    wordPadding                     Pad4bits,
    signal                          SBASSignalID,
    wordPadding1                    Pad5bits,
    iods                            Unsigned3,              -- Issue of Data Service
    wordPadding2                    Pad5bits,
    msgCount                        Unsigned3,              -- Number of service messages
    wordPadding3                    Pad5bits,
    msgNumber                       Unsigned3,              -- Service message number
    wordPadding4                    Pad5bits,
    regionCount                     Unsigned3,              -- Number of regions
    wordPadding5                    Pad6bits,
    priorityCode                    Unsigned2,
    wordPadding6                    Pad4bits,
    deltaUDREInside                 Unsigned4,              -- Delta UDRE Inside
    wordPadding7                    Pad4bits,
    deltaUDREOutside                Unsigned4,              -- Delta UDRE Outside
    wordPadding8                    Pad8bits,
    regions                         SEQUENCE (SIZE(5)) OF SEQUENCE {
        wordPadding                     Pad8bits,
        c1Lat                           INTEGER (-90..90),      -- Coordinate 1 latitude degrees
        wordPadding1                    Pad7bits,
        c1Lon                           INTEGER (-180..180),    -- Coordinate 1 longitude degrees
        wordPadding2                    Pad8bits,
        c2Lat                           INTEGER (-90..90),      -- Coordinate 2 latitude degrees
        wordPadding3                    Pad7bits,
        c2Lon                           INTEGER (-180..180),    -- Coordinate 2 longitude degrees
        wordPadding4                    Pad15bits,
        shape                           Unsigned1
    },
    wordPadding9                    Pad1bits,
    spare                           Unsigned15
}


-- ****************************************************************************
-- * SBAS Message Type 28 - Clock-Ephemeris Covariance Matrix                 *
-- *                                                                          *
-- * Message name:    DataSBAS28Unscaled                                      *
-- * Message ID:      6334                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 28 - Provides SBAS Clock-Ephemeris Covariance Matrix.  *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS28Unscaled ::= SEQUENCE {
    validityTime                    TimeStamp,
    satID                           SatID,
    dataSource                      DataSource,
    wordPadding                     Pad4bits,
    signal                          SBASSignalID,
    iodP                            Unsigned2,              -- IOD PRN
    satelliteMatrix                 SEQUENCE (SIZE(2)) OF SEQUENCE {
        prnMask                         Unsigned6,              -- PRN Mask Number
        scaleExponent                   Unsigned3,              -- Scale exponent
        e11                             Unsigned9,              -- unitless
        e22                             Unsigned9,              -- unitless
        e33                             Unsigned9,              -- unitless
        e44                             Unsigned9,              -- unitless
        e12                             Unsigned10,             -- unitless
        e13                             Unsigned10,             -- unitless
        e14                             Unsigned10,             -- unitless
        e23                             Unsigned10,             -- unitless
        e24                             Unsigned10,             -- unitless
        e34                             Unsigned10              -- unitless
    },
    wordPadding1                    Pad12bits
}


-- ****************************************************************************
-- * SBAS Message Type 28 - Clock-Ephemeris Covariance Matrix                 *
-- *                                                                          *
-- * Message name:    DataSBAS28Scaled                                        *
-- * Message ID:      6369                                                    *
-- * Message status:  Optional(1)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * SBAS Message Type 28 - Provides SBAS Clock-Ephemeris Covariance Matrix.  *
-- *                                                                          *
-- * Notes:                                                                   *
-- *                                                                          *
-- * Details can be found in: Minimum Operational Performance Standards       *
-- * For Global Positioning System/Wide Area Augmentation System Airborne     *
-- * Equipment.                                                               *
-- *                                                                          *
-- ****************************************************************************
--
DataSBAS28Scaled ::= SEQUENCE {
    validityTime                    TimeStamp,
    satID                           SatID,
    dataSource                      DataSource,
    wordPadding                     Pad4bits,
    signal                          SBASSignalID,
    wordPadding1                    Pad14bits,
    iodP                            INTEGER (0..3),         -- IOD PRN
    satelliteMatrix                 SEQUENCE (SIZE(2)) OF SEQUENCE {
        wordPadding                     Pad10bits,
        prnMask                         INTEGER (0..51),        -- PRN Mask Number
        wordPadding1                    Pad13bits,
        scaleExponent                   INTEGER (0..7),         -- Scale exponent
        wordPadding2                    Pad7bits,
        e11                             INTEGER (0..511),       -- unitless
        wordPadding3                    Pad7bits,
        e22                             INTEGER (0..511),       -- unitless
        wordPadding4                    Pad7bits,
        e33                             INTEGER (0..511),       -- unitless
        wordPadding5                    Pad7bits,
        e44                             INTEGER (0..511),       -- unitless
        wordPadding6                    Pad6bits,
        e12                             INTEGER (-512..511),    -- unitless
        wordPadding7                    Pad6bits,
        e13                             INTEGER (-512..511),    -- unitless
        wordPadding8                    Pad6bits,
        e14                             INTEGER (-512..511),    -- unitless
        wordPadding9                    Pad6bits,
        e23                             INTEGER (-512..511),    -- unitless
        wordPadding10                   Pad6bits,
        e24                             INTEGER (-512..511),    -- unitless
        wordPadding11                   Pad6bits,
        e34                             INTEGER (-512..511)     -- unitless
    }
}


-- ****************************************************************************
-- * UTC Corrections Messages                                                 *
-- *                                                                          *
-- * Message name:    DataUTCCorrections                                      *
-- * Message ID:      6421                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message contains the broadcast UTC correction factors received from *
-- * a single tracked GPS or Galileo satellite.                               *
-- *                                                                          *
-- * Notes:                                                                   *
-- *                                                                          *
-- * The GPS and Galileo UTC Correction Parameters can be consolidated        *
-- * together.                                                                *
-- *                                                                          *
-- * Note, the 2nd order term of the polynomial A2 is only available from the *
-- * GPS CNAV/CNAV2 transmissions.                                            *
-- *                                                                          *
-- * Note that A2 is set to 0 if it is not present in the broadcast signal.   *
-- *                                                                          *
-- ****************************************************************************
--
DataUTCCorrections ::= SEQUENCE {
    validityTime                    TimeStamp,
    signal                          SignalID,
    satID                           SatID,
    a0                              IEEE754Dp,              -- seconds
    a1                              IEEE754Sp,              -- seconds/second
    wordPadding                     Pad8bits,
    deltaTLS                        Signed8,                -- seconds: Leap second count before leap second adjustment
    wordPadding1                    Pad12bits,
    utcDataReferenceTimeOfWeek      INTEGER (0..1048560),   -- seconds of week
    utcDataReferenceWeekNumber      Unsigned8,              -- weeks
    weekNumberOfLeapSecAdjustment   Unsigned8,              -- weeks
    deltaTLSF                       Signed8,                -- seconds: Leap second count after leap second adjustment
    wordPadding2                    Pad5bits,
    -- dayNumber: Day number at the end of which a leap second adjustment becomes effective.
    -- 0 is not valid; the broadcast day number will be in the range 1..7.
    dayNumber                       INTEGER (0..7),
    a2                              IEEE754Sp               -- seconds/second/second
}


-- ****************************************************************************
-- * Waypoint Information                                                     *
-- *                                                                          *
-- * Message name:    DataWaypointInfo                                        *
-- * Message ID:      6445                                                    *
-- * Message status:  Optional(2)                                             *
-- * Frequency:       Once (per request)                                      *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message allows the waypoint information to be set or output.        *
-- *                                                                          *
-- * Notes:                                                                   *
-- *                                                                          *
-- * WaypointID 0 is special, meaning current waypoint, or all waypoints,     *
-- * depending on context, and should not be used here.                       *
-- *                                                                          *
-- ****************************************************************************
--
DataWaypointInfo ::= SEQUENCE {
    numberOfMessages                Unsigned8,              -- Number of messages to be sent (N)
    messageNumber                   Unsigned8,              -- Number of message (0 to N-1)
    wordPadding                     Pad6bits,
    waypointInfo                    SEQUENCE (SIZE(0..1023)) OF SEQUENCE {
        waypointID                      WaypointID,             -- WaypointID 0 is not a real waypoint and is not valid here
        position                        Position
    }
}


-- ****************************************************************************
-- * Route Information                                                        *
-- *                                                                          *
-- * Message name:    DataRouteInfo                                           *
-- * Message ID:      6325                                                    *
-- * Message status:  Optional(2)                                             *
-- * Frequency:       Once (per request)                                      *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message allows the route information to be set or output.           *
-- *                                                                          *
-- * Notes:                                                                   *
-- *                                                                          *
-- * RouteID 0 is special, meaning current route, or all routes, depending    *
-- * on context, and should not be used here.                                 *
-- *                                                                          *
-- * WaypointID 0 is special, meaning current waypoint, or all waypoints,     *
-- * depending on context, and should not be used here.                       *
-- *                                                                          *
-- ****************************************************************************
--
DataRouteInfo ::= SEQUENCE {
    numberOfMessages                Unsigned8,              -- Number of messages to be sent (N)
    messageNumber                   Unsigned8,              -- Number of message (0 to N-1)
    routeID                         RouteID,
    wordPadding                     Pad6bits,
    waypointsInRoute                SEQUENCE (SIZE(0..1023)) OF WaypointID  -- WaypointID 0 is not a real waypoint and is not valid here
}


-- ****************************************************************************
-- * Route Waypoint Navigation                                                *
-- *                                                                          *
-- * Message name:    DataRouteWaypointNav                                    *
-- * Message ID:      6410                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message supports navigation between waypoints (for both route and   *
-- * waypoint navigation).                                                    *
-- *                                                                          *
-- * Notes:                                                                   *
-- *                                                                          *
-- * For the case of 'waypoint' navigation, a single WaypointID is provided   *
-- * (toWaypoint).                                                            *
-- *                                                                          *
-- ****************************************************************************
--
DataRouteWaypointNav ::= SEQUENCE {
    validityTime                    TimeStamp,
    applicableRouteID               RouteID,                -- A RouteID, or 0 to indicate waypoint navigation.
    navigateToWaypoint              WaypointIndex,          -- Route waypoint index, or 0 if this is waypoint navigation.
    navigateFromWaypoint            WaypointIndex,          -- Route waypoint index, or 0 if this is waypoint navigation.
    fixStatus                       FixStatus,
    positionFigureOfMerit           PositionFigureOfMerit,
    magneticCorrectionSource        MagneticVariationSource,
    qFlag                           QFlag,
    fixAided                        BOOLEAN,
    useVerticalGuidance             BOOLEAN,
    wordPadding                     Pad1bits,
    toWaypoint                      ToWaypoint,             -- information for the next waypoint
    fromWaypoint                    FromWaypoint,           -- valid only if navigateFromWaypoint field is not set to 0.
    endWaypoint                     EndWaypoint             -- same as toWaypoint for waypoint navigation or the final waypoint for route navigation
}

EndWaypoint ::= SEQUENCE {
    waypointID                      WaypointID,
    waypointPosition                Position,
    distanceToWaypoint              IEEE754Sp,              -- metres (via any intermediary waypoints using great circle routes)
    timeToWaypoint                  IEEE754Sp,              -- seconds (via any intermediary waypoints using great circle routes)
    trackToWaypoint                 AngularDir              -- track bearing and reference
}

ToWaypoint ::= SEQUENCE {
    waypointID                      WaypointID,
    waypointPosition                Position,
    distanceToWaypoint              IEEE754Sp,              -- metres
    timeToWaypoint                  IEEE754Sp,              -- seconds
    trackToWaypoint                 AngularDir,             -- track bearing and reference
    verticalSlantAngleToWaypoint    IEEE754Sp,              -- degrees (-90.0 <= value <= +90.0)
    climbRateToWaypoint             IEEE754Sp               -- metres/second
}

FromWaypoint ::= SEQUENCE {
    waypointID                      WaypointID,
    waypointPosition                Position,
    distanceFromWaypoint            IEEE754Sp,              -- metres
    trackFromWaypoint               AngularDir,             -- track bearing and reference
    verticalSlantAngleFromWaypoint  IEEE754Sp               -- degrees (-90.0 <= value <= +90.0)
}


-- ****************************************************************************
-- * Waypoint Reached Alert                                                   *
-- *                                                                          *
-- * Message name:    DataWaypointReachedAlert                                *
-- * Message ID:      6263                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message provides an alert when a waypoint is reached.               *
-- *                                                                          *
-- * Notes:                                                                   *
-- *                                                                          *
-- ****************************************************************************
--
DataWaypointReachedAlert ::= SEQUENCE {
    validityTime                    TimeStamp,
    applicableRouteID               RouteID,                -- RouteID will be 0 if this is a waypoint only alert.
    waypointIndexReached            WaypointIndex,          -- Index will be 0 if not navigating a route.
    waypointIDReached               WaypointID
}


-- ****************************************************************************
-- * Provides Position Relative to a Waypoint Reference                       *
-- *                                                                          *
-- * Message name:    DataRelativePosition                                    *
-- * Message ID:      6308                                                    *
-- * Message status:  Optional(2)                                             *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * This message provides relative navigation (also known as 'Bullseye       *
-- * Navigation') by reporting current distance and bearing from a reference  *
-- * position waypoint 'Bullseye' set with CmndSelectReferenceWaypoint.       *
-- *                                                                          *
-- * Notes:                                                                   *
-- * Set the required waypoint number using CmndSelectReferenceWaypoint prior *
-- * to connecting to this message.                                           *
-- *                                                                          *
-- ****************************************************************************
--
DataRelativePosition ::= SEQUENCE {
    validityTime                    TimeStamp,
    fixStatus                       FixStatus,
    positionFigureOfMerit           PositionFigureOfMerit,
    magneticCorrectionSource        MagneticVariationSource,
    qFlag                           QFlag,
    fixAided                        BOOLEAN,
    useVerticalGuidance             BOOLEAN,
    wordPadding                     Pad1bits,
    referenceID                     WaypointID,
    referencePosition               Position,               -- 'Bullseye' location
    distanceFromReference           IEEE754Sp,              -- metres
    trackFromReference              AngularDir,             -- track bearing and reference
    verticalSlantAngleFromReference IEEE754Sp               -- degrees (-90.0 <= value <= +90.0)
}


-- ****************************************************************************
-- * Datum Information                                                        *
-- *                                                                          *
-- * Message name:    DataDatumInfo                                           *
-- * Message ID:      6446                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message allows the datum transformation parameters for              *
-- * transformations from alternative datums to the WGS-84 datum to be output *
-- * and input. Only the user defined datums can be set or read.              *
-- *                                                                          *
-- * Notes:                                                                   *
-- *                                                                          *
-- * Only those datums specified as user defined datums may have their        *
-- * parameters set by the user.                                              *
-- *                                                                          *
-- * The parameters set should be for transformation FROM the user defined    *
-- * datum to WGS-84 and should follow the sign conventions outlined in NATO  *
-- * STANAG 2211.                                                             *
-- *                                                                          *
-- ****************************************************************************
--
DataDatumInfo ::= SEQUENCE {
    wordPadding                     Pad12bits,
    datumInfo                       SEQUENCE (SIZE(0..10)) OF SEQUENCE {
        datumID                         DatumID,            -- A user defined datum (see DatumID user0 to user9)
        a                               IEEE754Dp,          -- Length of semi-major axis of the ellipsoid (in metres)
        e2                              IEEE754Dp,          -- Square of the eccentricity of the ellipsoid
        dx                              IEEE754Sp,          -- Shift in X-coordinate (in metres)
        dy                              IEEE754Sp,          -- Shift in Y-coordinate (in metres)
        dz                              IEEE754Sp,          -- Shift in Z-coordinate (in metres)
        ds                              IEEE754Sp,          -- Scale change (ppm)
        rx                              IEEE754Sp,          -- Rotation about X-axis (in arcseconds)
        ry                              IEEE754Sp,          -- Rotation about Y-axis (in arcseconds)
        rz                              IEEE754Sp,          -- Rotation about Z-axis (in arcseconds)
        transformationAccuracyValid     BOOLEAN,
        wordPadding                     Pad7bits,
        accuracyX                       Unsigned8,          -- metres (1 sigma accuracy)
        accuracyY                       Unsigned8,          -- metres (1 sigma accuracy)
        accuracyZ                       Unsigned8           -- metres (1 sigma accuracy)
    }
}


-- ****************************************************************************
-- * Atmospheric Corrections                                                  *
-- *                                                                          *
-- * Message name:    DataAtmosphericCorrections                              *
-- * Message ID:      6401                                                    *
-- * Message status:  Core                                                    *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * The atmospheric corrections message returns information about the        *
-- * methods used to correct for atmospheric delays and the correction        *
-- * values themselves.                                                       *
-- *                                                                          *
-- * Notes:                                                                   *
-- *                                                                          *
-- * Ionospheric correction is frequency dependant, the value given is        *
-- * referenced to the signal indicated by SignalID. The user can scale this  *
-- * value to other frequencies to find the correction applied to other       *
-- * signals.                                                                 *
-- *                                                                          *
-- ****************************************************************************
--
DataAtmosphericCorrections ::= SEQUENCE {
    validityTime                    TimeStamp,
    numberOfMessages                Unsigned8,              -- Number of messages to be reported this epoch (N)
    messageNumber                   Unsigned8,              -- Number of message being reported (0 to N-1)
    atmosphericCorrectionInfos      AtmosphericCorrectionInfos
}

AtmosphericCorrectionInfos ::= SEQUENCE {
    atmosphericCorrectionInfos      SEQUENCE (SIZE(0..65535)) OF SEQUENCE {
        signalID                        SignalID,
        satID                           SatID,
        wordPadding                     Pad4bits,
        ionoCorrectionInUse             IonoCorrection,
        wordPadding1                    Pad4bits,
        tropoCorrectionInUse            TropoCorrection,
        ionoCorrection                  IEEE754Sp,              -- metres
        tropoCorrection                 IEEE754Sp               -- metres
    }
}


-- ****************************************************************************
-- * Receiver Clock Bias Message                                              *
-- *                                                                          *
-- * Message name:    DataRxClockBias                                         *
-- * Message ID:      6266                                                    *
-- * Message status:  Optional(2)                                             *
-- * Frequency:       As required                                             *
-- * Input/Output:    Input/Output                                            *
-- *~~~~~~~~~~~~~~~~~~~~~~~~~~~~~~~~~~~~~~~~~~~~~~~~~~~~~~~~~~~~~~~~~~~~~~~~~~*
-- * Short Description:                                                       *
-- *                                                                          *
-- * This message provides information about the receiver clock bias and      *
-- * drift with respect to the given biasTimeRef.                             *
-- *                                                                          *
-- * Notes:                                                                   *
-- * A positive rxClockBias value means the rxClock is ahead of the given     *
-- * biasTimeRef.                                                             *
-- *                                                                          *
-- * In some scenarios the clock bias/drift reported may be with respect to a *
-- * different time reference than validityTime. It is therefore important to *
-- * note the time reference indicated by biasTimeRef.                        *
-- *                                                                          *
-- ****************************************************************************
--
DataRxClockBias ::= SEQUENCE {
    validityTime                    TimeStamp,
    wordPadding                     Pad4bits,
    fixStatus                       FixStatus,
    wordPadding1                    Pad4bits,
    timeFigureOfMerit               TimeFigureOfMerit,
    wordPadding2                    Pad12bits,
    biasTimeRef                     TimeReference,
    rxClockBias                     IEEE754Dp,              -- seconds - see Notes for the sense
    rxClockDrift                    IEEE754Sp               -- seconds/second
}


-- ****************************************************************************
-- * User Messages                                                            *
-- *                                                                          *
-- * Message name:    DataUserMessages                                        *
-- * Message ID:      6353                                                    *
-- * Message status:  Core                                                    *
-- * Frequency:       As required                                             *
-- * Input/Output:    Output                                                  *
-- *~~~~~~~~~~~~~~~~~~~~~~~~~~~~~~~~~~~~~~~~~~~~~~~~~~~~~~~~~~~~~~~~~~~~~~~~~~*
-- * Short Description:                                                       *
-- *                                                                          *
-- * Returns the 'User Messages' encoded in the NAV data.                     *
-- *                                                                          *
-- * Notes:                                                                   *
-- *                                                                          *
-- * For GPS LNAV the 'special' message, from subframe 4, page 17, consists   *
-- * of 22 octets, from a limited character set (see IS-GPS-200).             *
-- *                                                                          *
-- * For GPS CNAV the type 36 and 15 'text' message consists of 18 and 29     *
-- * octets respectively, again from a limited character set (see             *
-- * IS-GPS-200).                                                             *
-- *                                                                          *
-- * For GLONASS CNAV string type 60 contains 184 bits, or 23 octets.         *
-- *                                                                          *
-- * The messageString shall be tail padded, if necessary, with a null        *
-- * (0x00) octet to form an even number of octets. The messageString is      *
-- * then sent as a sequence of octet pair words as described in the main     *
-- * document (LSB then MSB).                                                 *
-- *                                                                          *
-- ****************************************************************************
--
DataUserMessages ::= SEQUENCE {
    validityTime                    TimeStamp,
    wordPadding                     Pad8bits,
    userMessage                     SEQUENCE (SIZE(0..255)) OF SEQUENCE {
        gnssSignal                      SignalID,
        satID                           SatID,
        wordPadding                     Pad8bits,
        messageString                   SEQUENCE (SIZE(0..255)) OF MessageOctet
    }
}


END
